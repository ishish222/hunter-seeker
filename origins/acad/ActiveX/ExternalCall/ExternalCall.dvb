Attribute VB_Name = "ThisDrawing"
Attribute VB_Base = "0{8E75D913-3D21-11D2-85C4-080009A0C626}"
Attribute VB_GlobalNameSpace = False
Attribute VB_Creatable = False
Attribute VB_PredeclaredId = True
Attribute VB_Exposed = True
Attribute VB_TemplateDerived = False
Attribute VB_Customizable = True
'      ActiveX Sample
'
'      Copyright (C) 1996, 1997, 1998, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.

Public Sub Run_Sample()
    UserForm1.Show
End Sub

Attribute VB_Name = "UserForm1"
Attribute VB_Base = "0{58E7022B-3F95-4329-901A-0F7B2B2F1673}{7CBAC499-1030-4D39-B0E0-3620D717DFB5}"
Attribute VB_GlobalNameSpace = False
Attribute VB_Creatable = False
Attribute VB_PredeclaredId = True
Attribute VB_Exposed = False
Attribute VB_TemplateDerived = False
Attribute VB_Customizable = False
'      ActiveX Sample
'
'      Copyright (C) 1996, 1997, 1998, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.

Private Sub ButtonCalculate_Click()
    Dim VB6DLL As Object
    Dim VB6FunctionReturnValue As Long
    Dim XLength As Double, YLength As Double, ZLength As Double

    ' We make sure the user entered numeric values that fit into a Double data type.
    On Error GoTo OverFlow
    
    ' Check X length.
    If Not (IsNumeric(TextBoxX.Text)) Then
        MsgBox "The X length must be numeric!", vbExclamation
        TextBoxX.SetFocus
        Exit Sub
    End If
    
    XLength = CDbl(TextBoxX.Text)

    ' Check Y length.
    If Not (IsNumeric(TextBoxY.Text)) Then
        MsgBox "The Y length must be numeric!", vbExclamation
        TextBoxY.SetFocus
        Exit Sub
    End If
    
    YLength = CDbl(TextBoxY.Text)
    
    ' Check Z length.
    If Not (IsNumeric(TextBoxZ.Text)) Then
        MsgBox "The Z length must be numeric!", vbExclamation
        TextBoxZ.SetFocus
        Exit Sub
    End If
    
    ZLength = CDbl(TextBoxZ.Text)
       
    On Error GoTo ErrorTrap
    
    ' The values are numeric, and we have an error-trapping statement.
    ' Now the values will be sent to the Visual Basic 6 component for processing.
 
    ' We connect to the class containing our external function.
    ' This function is contained in a DLL created with VB6.
    Set VB6DLL = ThisDrawing.Application.GetInterfaceObject("ExternalFunction.MyClass")
    
    ' We send information from our form to the external function.
    VB6FunctionReturnValue = VB6DLL.CubeVolume(XLength, YLength, ZLength)

    ' We display the value returned from VB6 DLL.
    TextBoxTotal.Text = VB6FunctionReturnValue
    
    Exit Sub

ErrorTrap:
    MsgBox "An error was generated.  The error description is: " & Err.Description, vbExclamation
    Exit Sub
    
OverFlow:
    MsgBox "One of the lengths entered is too large, please try again.", vbExclamation
    Exit Sub

End Sub

Private Sub ButtonCancel_Click()
    UserForm1.Hide
End Sub

Private Sub UserForm_Click()

End Sub
