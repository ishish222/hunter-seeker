Attribute VB_Name = "Extract_Form"
Attribute VB_Base = "0{33DF9F7B-35E7-4BDF-B22F-87A563B25F02}{406F9E2E-A5D9-436B-B225-C52480BCF604}"
Attribute VB_GlobalNameSpace = False
Attribute VB_Creatable = False
Attribute VB_PredeclaredId = True
Attribute VB_Exposed = False
Attribute VB_TemplateDerived = False
Attribute VB_Customizable = False
'      VBA Sample
'
'      Copyright (C) 1996, 1997, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'
Option Explicit

Private Sub cmdCancel_Click()
    Unload Me
End Sub

Private Sub cmdStart_Click()
    Dim Excel As Object
    Dim elem As Object
    Dim excelSheet As Object
    Dim Array1 As Variant
    Dim Count, RowNum As Integer
    Dim NumberOfAttributes As Integer
    
    ' Start Excel
    On Error Resume Next
    
    Set Excel = GetObject(, "Excel.Application")
    
    If Err <> 0 Then
        Err.Clear
        Set Excel = CreateObject("Excel.Application")
            
        If Err <> 0 Then
            MsgBox "Could not load Excel.", vbExclamation
            End
        End If
    End If
    
    On Error GoTo 0
    
    Excel.Visible = True
    Excel.Workbooks.Add
    Excel.Sheets("Sheet1").Select
    Set excelSheet = Excel.ActiveWorkbook.Sheets("Sheet1")
    
    RowNum = 1
    Dim Header As Boolean
    For Each elem In ThisDrawing.ModelSpace
        If StrComp(elem.EntityName, "AcDbBlockReference", 1) = 0 Then
            If elem.HasAttributes Then
                Array1 = elem.GetAttributes
                For Count = LBound(Array1) To UBound(Array1)
                    If Header = False Then
                        If StrComp(Array1(Count).EntityName, "AcDbAttribute", 1) = 0 Then
                            excelSheet.Cells(RowNum, Count + 1).Value = Array1(Count).TagString
                        End If
                    End If
                Next Count
                RowNum = RowNum + 1
                For Count = LBound(Array1) To UBound(Array1)
                    excelSheet.Cells(RowNum, Count + 1).Value = Array1(Count).TextString
                Next Count
                Header = True
            End If
        End If
    Next elem
    
    NumberOfAttributes = RowNum - 1
    
    If NumberOfAttributes > 0 Then
        excelSheet.Range(Cells(1, 1), Cells(1, 100)).Font.Bold = True
        
        'For a specific set of attribute information this could
        'be set to fit the exact number of columns.
        excelSheet.Columns("A:G").AutoFit
        'Rename the worksheet
        Sheets("Sheet1").Name = "Attributes"
        If Chart.Value = True Then
            CreateChart (NumberOfAttributes)
        End If
        If Memo.Value = True Then
            MakeMemos
        End If
    Else
        MsgBox "No attributes found in the current drawing.", vbInformation
        Excel.Quit
    End If
    
    Unload Me
End Sub

Private Sub UserForm_Click()

End Sub

Attribute VB_Name = "Module1"
'      VBA Sample
'
'      Copyright (C) 1996, 1997, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'
Option Explicit

Sub CreateChart(NumberOfBlocks As Integer)
    Dim ChartRange As Object
    Static NewChart As Chart
    ' Change the range to pick up the correct data for a chart
    ' Skip the header, and add 1 to the total number of blocks
    Set ChartRange = ActiveSheet.Range(Cells(2, 1), Cells(NumberOfBlocks + 1, 10))
    ChartRange.Select
    Set NewChart = Charts.Add
    NewChart.Activate
    With NewChart
        .Type = xl3DColumn
        .CopyPicture xlScreen
    End With
End Sub

Sub MakeMemos()
    Dim Word As Object
    Set Word = CreateObject("Word.Basic")
    
    Dim sMyDocumentsDirectory As String
    Dim wshShell
    Set wshShell = CreateObject("WScript.Shell")
    sMyDocumentsDirectory = wshShell.SpecialFolders("MyDocuments")

    With Word
        .FileNewDefault
        .Insert "M E M O R A N D U M"
        .InsertPara
        .InsertPara
        .Insert "Date:" & Chr(9) & Format(Date, "mmm d, yyyy")
        .InsertPara
  

        .Insert "To: <Insert Name Here>"
        .InsertPara
        .Insert "From: <Your Name>"
        .InsertPara
        .Insert "Title "
        ' Uncomment the following lines to automatically copy the
        ' clipboard contents into the document.
        ' Word.EditPaste
        ' .Insert Message
        .InsertPara
        .InsertPara
        .InsertChart
        .InsertPara
        .Insert "Insert your memo text here..."
        .InsertPara
        .StartOfDocument
        .EndOfLine 1
        .Bold
        .CenterPara
        .FileSaveAs sMyDocumentsDirectory + "\demo.doc"
       .DocClose
    End With
    
    Set Word = Nothing

    MsgBox "The memo has been created and saved in " + sMyDocumentsDirectory + "\demo.doc.", vbInformation
End Sub


Sub Extract_Dialog()
    Extract_Form.Show
End Sub
