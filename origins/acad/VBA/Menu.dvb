Attribute VB_Name = "ThisDrawing"
Attribute VB_Base = "0{8E75D913-3D21-11D2-85C4-080009A0C626}"
Attribute VB_GlobalNameSpace = False
Attribute VB_Creatable = False
Attribute VB_PredeclaredId = True
Attribute VB_Exposed = True
Attribute VB_TemplateDerived = False
Attribute VB_Customizable = True
'      VBA Sample
'
'      Copyright (C) 1996, 1997, 1998, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.

Public Sub addMenuItem()
    'creates a new submenu on the Modify menu called "Mymodify"
    Dim oAcad As AcadApplication
    Set oAcad = ThisDrawing.Application
    Dim oPopup As AcadPopupMenu
    Dim oSubPopup As AcadPopupMenu
    Dim oPopupMenuItem As AcadPopupMenuItem
    For Each oPopup In oAcad.MenuBar
        'TagString is not localized so use it to locate the menu
        If oPopup.TagString = "ID_MnModify" Then
            Set oSubPopup = oPopup.AddSubMenu(0, "MyModify")
            'set TagString to a known value; we'll use this during removal
            oSubPopup.Parent.TagString = "ID_MyModify"
            Set oPopupMenuItem = oSubPopup.addMenuItem(0, "MenuItem1", "command1 ")
            oPopupMenuItem.HelpString = "This is the helpstring for command1"
            Set oPopupMenuItem = oSubPopup.addMenuItem(1, "MenuItem2", "command2 ")
            oPopupMenuItem.HelpString = "This is the helpstring for command2"
            Set oPopupMenuItem = oSubPopup.addMenuItem(2, "MenuItem3", "command3 ")
            oPopupMenuItem.HelpString = "This is the helpstring for command3"
            oPopupMenuItem.Check = True
            Exit For
        End If
    Next oPopup
End Sub

Public Sub removeMenuItem()
    'this macro removes the submenu created by the addMenuItem macro
    Dim oAcad As AcadApplication
    Set oAcad = ThisDrawing.Application
    Dim oPopup As AcadPopupMenu
    Dim oPopupItem As AcadPopupMenuItem
    For Each oPopup In oAcad.MenuBar
        'TagString is not localized, so use it to locate the menu
        If oPopup.TagString = "ID_MnModify" Then
            For Each oPopupItem In oPopup
                If oPopupItem.TagString = "ID_MyModify" Then
                    oPopupItem.Delete
                    Exit For
                End If
            Next oPopupItem
            Exit For
        End If
    Next oPopup
End Sub

Public Sub DisableMenuItem()
    'this macro disables the exit item on the File menu
    Dim oAcad As AcadApplication
    Set oAcad = ThisDrawing.Application
    Dim oPopup As AcadPopupMenu
    Dim oPopupItem As AcadPopupMenuItem
    For Each oPopup In oAcad.MenuBar
        'TagString is not localized so use it to locate the menu
        If oPopup.TagString = "ID_MnFile" Then
            For Each oPopupItem In oPopup
                If oPopupItem.TagString = "ID_Quit" Then
                    oPopupItem.Enable = False
                    Exit For
                End If
            Next oPopupItem
            Exit For
        End If
    Next oPopup
End Sub

Public Sub EnableMenuItem()
    'this macro enables the exit item on the File menu
    Dim oAcad As AcadApplication
    Set oAcad = ThisDrawing.Application
    Dim oPopup As AcadPopupMenu
    Dim oPopupItem As AcadPopupMenuItem
    For Each oPopup In oAcad.MenuBar
        'TagString is not localized so use it to locate the menu
        If oPopup.TagString = "ID_MnFile" Then
            For Each oPopupItem In oPopup
                If oPopupItem.TagString = "ID_Quit" Then
                    oPopupItem.Enable = True
                    Exit For
                End If
            Next oPopupItem
            Exit For
        End If
    Next oPopup
End Sub

Public Sub ShowToolbar()
    'this macro shows the Insert toolbar
    'and adds a new button to it
    Dim oAcad As AcadApplication
    Set oAcad = ThisDrawing.Application
    Dim oToolbar As AcadToolbar
    Dim oToolbarItem As AcadToolbarItem
    For Each oToolbar In oAcad.MenuGroups("ACAD").Toolbars
        'TagString is not localized
        If oToolbar.TagString = "TB_0001" Then 'insert toolbar
            oToolbar.Visible = True
            Set oToolbarItem = oToolbar.AddToolbarButton(oToolbar.Count + 1, "Open", "Opens a file", "._open ")
            'set TagString to a known value; we'll use this during removal
            oToolbarItem.TagString = "ID_Open"
            'note that the bitmaps are now picked up from AutoCAD's resources as
            'we operate on the AutoCAD menu group
            oToolbarItem.SetBitmaps "RCDATA_16_OPEN", "RCDATA_16_OPEN"
            Exit For
        End If
    Next oToolbar
End Sub

Public Sub RemoveButton()
    'this macro removes the button added by ShowToolbar from the Insert toolbar
    On Error Resume Next
    Dim oAcad As AcadApplication
    Set oAcad = ThisDrawing.Application
    Dim oToolbar As AcadToolbar
    Dim oToolbarItem As AcadToolbarItem
    For Each oToolbar In oAcad.MenuGroups("ACAD").Toolbars
        'TagString is not localized
        If oToolbar.TagString = "TB_0001" Then
            For Each oToolbarItem In oToolbar
                If oToolbarItem.TagString = "ID_Open" Then
                    oToolbarItem.Delete
                    Exit For
                End If
            Next oToolbarItem
            Exit For
        End If
    Next oToolbar
End Sub
