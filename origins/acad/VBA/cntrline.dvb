Attribute VB_Name = "AutomaticCenterLines"
'      VBA Sample
'
'      Copyright (C) 1996, 1997, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'
'      Originally submitted by Eric B Howard (Ace VBA Alpha Tester) at Synergis Technologies

Option Explicit

Const Pi = 3.141592654
Function Distance(p1() As Double, p2() As Double) As Double
    Dim xDist As Double
    Dim yDist As Double
    Dim zDist As Double
    
    xDist = p1(0) - p2(0)
    yDist = p1(1) - p2(1)
    zDist = p1(2) - p2(2)
    Distance = Sqr(xDist ^ 2 + yDist ^ 2 + zDist ^ 2)
End Function
Sub FillArray(Source As Variant, Dest As Variant)
'Takes the values from Source and fills Dest with them
'Source is the full array
'Dest is the array to be filled
    Dim nIdx As Long
    
    'Check to see if both arrays are the same size
    If (UBound(Source) - LBound(Source)) = (UBound(Dest) - LBound(Dest)) Then
        nIdx = LBound(Source)
        While nIdx <= UBound(Source)
            Dest(nIdx) = Source(nIdx)
            nIdx = nIdx + 1
        Wend
    End If
End Sub
Function LayerExist(ByVal LayerName As String) As Boolean
    Dim Element As Object
            
    LayerExist = False
    For Each Element In ThisDrawing.Layers
        If Element.Name = UCase(LayerName) Then
            LayerExist = True
            Exit For
        End If
    Next
End Function
Function LinetypeExist(ByVal LTypeName As String) As Boolean
    Dim Element As Object
            
    LinetypeExist = False
    For Each Element In ThisDrawing.Linetypes
        If Element.Name = UCase(LTypeName) Then
            LinetypeExist = True
            Exit For
        End If
    Next
End Function
Private Sub InitializeLayer(LayerName As String, LayerLType As String, LayerColor As Long)
    Dim LoseReturn As Long
    Dim NewLayer As IAcadLayer
    
    If LayerExist(LayerName) = False Then
        ' If Linetype is not loaded, then load it
        If LinetypeExist(LayerLType) = False Then
            ThisDrawing.Linetypes.Load LayerLType, "acad.lin"
        End If
        ' Create Layer
        Set NewLayer = ThisDrawing.Layers.Add(LayerName)
        NewLayer.Color = LayerColor
        NewLayer.Linetype = LayerLType
    End If
End Sub
Sub AutomaticCenterLines()
    Const LineExtension = 0.25
    Const LineMultiplier = 1.75
    Const LayerName = "Center"
    Const LayerColor = 30
    Const LayerLType = "Center"

    Dim SSet As AcadSelectionSet
    Dim CurrentSpace As Long
    Dim Element As Object
    Dim CenterPoint(0 To 2) As Double
    Dim EndPoint1(0 To 2) As Double
    Dim EndPoint2(0 To 2) As Double
    Dim Cline As AcadLine
    Dim LineHalfLength As Double
    Dim GroupCode(0 To 4) As Integer
    Dim DataValue(0 To 4) As Variant
    
    MsgBox "Select Arcs, Circles, and Ellipses to be Centerlined"
    
 On Error Resume Next
 ' Delete the selection set if it exists
 If Not IsNull(ThisDrawing.SelectionSets.Item("ArcsCirclesEllipses")) Then
    Set SSet = ThisDrawing.SelectionSets.Item("ArcsCirclesEllipses")
    SSet.Delete
 End If
    
    Set SSet = ThisDrawing.SelectionSets.Add("ArcsCirclesEllipses")
    'Set up selection set filter
    GroupCode(0) = -4
    DataValue(0) = "<or"
    GroupCode(1) = 0
    DataValue(1) = "Arc"
    GroupCode(2) = 0
    DataValue(2) = "Circle"
    GroupCode(3) = 0
    DataValue(3) = "Ellipse"
    GroupCode(4) = -4
    DataValue(4) = "or>"
    SSet.SelectOnScreen GroupCode, DataValue
    For Each Element In SSet
        CurrentSpace = ThisDrawing.ActiveSpace
        InitializeLayer LayerName, LayerLType, LayerColor
        
        If Element.EntityType = acCircle Or Element.EntityType = acArc Then
            Dim CurRadius As Double
        
            CurRadius = Element.Radius
            If CurRadius <= LineExtension Then
                LineHalfLength = LineMultiplier * CurRadius
            Else
                LineHalfLength = LineExtension + CurRadius
            End If
            FillArray Element.Center, CenterPoint
            'Create vertical line
            EndPoint1(0) = CenterPoint(0)
            EndPoint1(1) = CenterPoint(1) - LineHalfLength
            EndPoint1(2) = CenterPoint(2)
            EndPoint2(0) = CenterPoint(0)
            EndPoint2(1) = CenterPoint(1) + LineHalfLength
            EndPoint2(2) = CenterPoint(2)
            If CurrentSpace = acModelSpace Then
                Set Cline = ThisDrawing.ModelSpace.AddLine(EndPoint1, EndPoint2)
            Else
                Set Cline = ThisDrawing.PaperSpace.AddLine(EndPoint1, EndPoint2)
            End If
            Cline.Layer = LayerName
            'Create horizontal line
            EndPoint1(0) = CenterPoint(0) - LineHalfLength
            EndPoint1(1) = CenterPoint(1)
            EndPoint1(2) = CenterPoint(2)
            EndPoint2(0) = CenterPoint(0) + LineHalfLength
            EndPoint2(1) = CenterPoint(1)
            EndPoint2(2) = CenterPoint(2)
            If CurrentSpace = acModelSpace Then
                Set Cline = ThisDrawing.ModelSpace.AddLine(EndPoint1, EndPoint2)
            Else
                Set Cline = ThisDrawing.PaperSpace.AddLine(EndPoint1, EndPoint2)
            End If
            Cline.Layer = LayerName
        ElseIf Element.EntityType = acEllipse Then
            Dim MajorAxis(0 To 2) As Double
            Dim MinorAxis(0 To 2) As Double
            Dim QuadPoint(0 To 2) As Double
            Dim MajorRadiusAngle As Double
            Dim MinorRadius As Double
            Dim MajorRadius As Double
            Dim LineHalfLengthMinor As Double
            
            FillArray Element.Center, CenterPoint
            FillArray Element.MajorAxis, MajorAxis
            FillArray Element.MinorAxis, MinorAxis
            QuadPoint(0) = MajorAxis(0) + CenterPoint(0)
            QuadPoint(1) = MajorAxis(1) + CenterPoint(1)
            QuadPoint(2) = MajorAxis(2) + CenterPoint(2)
            MajorRadius = Distance(QuadPoint, CenterPoint)
            MinorRadius = MajorRadius * Element.RadiusRatio
            MajorRadiusAngle = ThisDrawing.Utility.AngleFromXAxis(CenterPoint, QuadPoint)
            If MinorRadius <= LineExtension Then
                LineHalfLengthMinor = LineMultiplier * MinorRadius
            Else
                LineHalfLengthMinor = LineExtension + MinorRadius
            End If
            If MajorRadius <= LineExtension Then
                LineHalfLength = LineMultiplier * MajorRadius
            Else
                LineHalfLength = LineExtension + MajorRadius
            End If
            'Draw the major axis centerline
            With ThisDrawing.Utility
                FillArray .PolarPoint(CenterPoint, MajorRadiusAngle, LineHalfLength), EndPoint1
                FillArray .PolarPoint(CenterPoint, MajorRadiusAngle + Pi, LineHalfLength), EndPoint2
            End With
            If CurrentSpace = acModelSpace Then
                Set Cline = ThisDrawing.ModelSpace.AddLine(EndPoint1, EndPoint2)
            Else
                Set Cline = ThisDrawing.PaperSpace.AddLine(EndPoint1, EndPoint2)
            End If
            Cline.Layer = LayerName
            'Draw the minor axis centerline
            With ThisDrawing.Utility
                FillArray .PolarPoint(CenterPoint, MajorRadiusAngle - (Pi / 2), LineHalfLengthMinor), EndPoint1
                FillArray .PolarPoint(CenterPoint, MajorRadiusAngle + (Pi / 2), LineHalfLengthMinor), EndPoint2
            End With
            If CurrentSpace = acModelSpace Then
                Set Cline = ThisDrawing.ModelSpace.AddLine(EndPoint1, EndPoint2)
            Else
                Set Cline = ThisDrawing.PaperSpace.AddLine(EndPoint1, EndPoint2)
            End If
            Cline.Layer = LayerName
        End If
    Next
End Sub
