Attribute VB_Name = "Module1"
'      VBA Sample
'
'      Copyright (C) 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'

Option Explicit

' Name of this sample. Used for message box titles.
Public Const conDemoName = "AutoCAD External Application Communication Sample"

' Name of Excel worksheeet
Public Const BOM_SHEET_NAME = "AutoCAD BOM"

' Name of block table entries
Public Const BOM_TITLE = "BOMTITLE"
Public Const BOM_ENTRY = "BOMLINE"

' Version of Excel that's available to us. This will be
' set to 7, 8, or 0 -- older versions will not work.
' Set by the ConnectExcel procedure
Public ExcelVer As Integer
Public ExcelServer As Object

' This is the main entry point for the sample.
Public Sub Run_Sample()
    Dim DrawingTest As AcadApplication
    
    On Error GoTo No_Drawing
    Set DrawingTest = ThisDrawing.Application
    On Error GoTo 0
        
    Userform1.Show
    
    Exit Sub
    
No_Drawing:
    MsgBox "You must load the sample drawing before running the macro.", vbExclamation
End Sub

Private Sub FormatWorkSheet(objWorksheet As Object, ByVal intRow As Integer)
    ' Format the Excel worksheet header and properly size the columns
    objWorksheet.Rows("1:1").Font.Bold = True
    objWorksheet.Rows("1:1").Interior.ColorIndex = 35
    objWorksheet.Columns("A:H").EntireColumn.AutoFit
End Sub

Public Sub GenerateDetailTable(X As Variant)
    ' X is only used to suppress this routine from the Run Macro dialog
    
    ' Create a report in Excel
    
    ' We have to late-bind the object because the user
    ' might not have Excel installed
    
    Dim objWorksheet As Object, objWorkBook As Object
    Dim intRow As Integer
    Dim fAlreadyRunning As Boolean
    Dim iCount As Integer
    
    On Error GoTo HandleErr
    
    ' Connect to Excel
    ConnectExcel 1
    If ExcelServer Is Nothing Then
        GoTo ExitHere
    End If

    ' Create new Excel workbook
    Set objWorkBook = ExcelServer.Workbooks.Add
    Set objWorksheet = objWorkBook.Sheets(1)
    objWorksheet.Name = BOM_SHEET_NAME

    ' Generate bill of materials from drawing data and send data to Excel
    intRow = ExportData(objWorksheet)

    ' Format the worksheet
    FormatWorkSheet objWorksheet, intRow
    
ExitHere:
    Set objWorksheet = Nothing
    
    Exit Sub
    
HandleErr:
    MsgBox "GenerateDetailTable error " & Err.Number & " (" & Err.Description & ") from " & _
            Err.Source, vbCritical, conDemoName
End Sub

Sub ImportData(X As Variant)
    ' X is only used to suppress this routine from the Run Macro dialog

    ' We have to late-bind the object because the user
    ' might not have Excel installed
    
    Dim objWorksheet As Object, objCell As Object
    Dim objAutoCad As Object, objModelSpace As AcadModelSpace, objEntity As Object
    Dim iRowNum As Long
    Dim TableData As Variant
    Dim iCount As Long
    Dim Header As Boolean
    Dim RowCount As Long
    Dim CurrentItem As String
    
    ' AutoCAD Table Index
    Const TABLE_ITEM_NUMBER = 0
    Const TABLE_PARTNUMBER = 1
    Const TABLE_DESCRIPTION = 2
    Const TABLE_QUANTITY = 3
    
    ' Excel column numbers
    Const CELL_ITEM_NUMBER = 1
    Const CELL_PARTNUMBER = 2
    Const CELL_DESCRIPTION = 3
    Const CELL_QUANTITY = 4
    
    On Error GoTo HandleErr

    ' Connect to Excel
    ConnectExcel 1
    If ExcelServer Is Nothing Then
        GoTo ExitHere
    End If
    
    ' Open the parts list in Excel
    On Error GoTo NO_BOM_WORKSHEET
    Set objWorksheet = ExcelServer.ActiveWorkbook.Worksheets(BOM_SHEET_NAME)
    On Error GoTo HandleErr
    
    ' Retrieve the AutoCAD modelspace, so we can look
    ' at the various entities in this drawing
    Set objAutoCad = ThisDrawing.Application
    Set objModelSpace = objAutoCad.ActiveDocument.ModelSpace()

    ' Walk through spreadsheet and grab data for our table in the drawing
    ' Note that we start at row 2 since we don't allow users to modify
    ' the header
    
    For iRowNum = 2 To 26              ' Table numbers are hardcoded for this sample
        
        CurrentItem = objWorksheet.Cells(iRowNum, CELL_ITEM_NUMBER).Value
        
        ' Look for corresponding table object and update data
        For Each objEntity In objModelSpace
            
            With objEntity
                
                If StrComp(.EntityName, "AcDbBlockReference", 1) = 0 Then
                    If .HasAttributes Then
                        TableData = .GetAttributes
                        
                        ' Make sure we have the correct table entry and
                        ' update with new data from Excel
                        If TableData(TABLE_ITEM_NUMBER).TextString = CurrentItem Then
                            TableData(TABLE_PARTNUMBER).TextString = objWorksheet.Cells(iRowNum, CELL_PARTNUMBER).Value
                            TableData(TABLE_DESCRIPTION).TextString = objWorksheet.Cells(iRowNum, CELL_DESCRIPTION).Value
                            TableData(TABLE_QUANTITY).TextString = objWorksheet.Cells(iRowNum, CELL_QUANTITY).Value
                        End If
                        
                    End If
                End If
            End With
        Next objEntity
    Next iRowNum
    
ExitHere:
    ' Regenerate to see new table
    ThisDrawing.Regen acAllViewports

    Exit Sub

NO_BOM_WORKSHEET:
    MsgBox "The AutoCAD bill of materials Worksheet was not found in the active Excel Workbook." & vbCrLf & vbCrLf & _
           "Please load or regenerate the Workbook containing this Worksheet and make it the active Workbook.", vbExclamation
    Exit Sub
    
HandleErr:
    MsgBox "ImportData error " & Err.Number & " (" & Err.Description & ") from " & _
            Err.Source, vbCritical, conDemoName
End Sub

Public Function ExportData(objWorksheet As Object) As Integer
    ' Fill the detail table with the info from the drawing
    Dim objAutoCad As Object, objModelSpace As Object, objEntity As Object
    Dim TableData As Variant
    Dim iCount As Long
    Dim fFound As Boolean
    Dim strTag As String
    Dim iRowNum As Integer
    Dim Header As Boolean
    Dim NumberOfAttributes  As Long
    
    On Error GoTo HandleErr
    
    ' Here we need to access the elements in the drawing and
    ' extract their attributes
    
    Set objAutoCad = ThisDrawing.Application

    Set objModelSpace = objAutoCad.ActiveDocument.ModelSpace()
    
    ' Walk through the drawing and look for block references
    ' with attributes. Note that the ModelSpace object is itself
    ' a collection of entity objects
    
    iRowNum = 1     ' Starting row in Excel
    
    For Each objEntity In objModelSpace
        With objEntity
            If StrComp(.EntityName, "AcDbBlockReference", 1) = 0 Then
                If .HasAttributes Then
                    
                    TableData = .GetAttributes
                    
                    For iCount = LBound(TableData) To UBound(TableData)
                        If Header = False Then
                            If StrComp(TableData(iCount).EntityName, "AcDbAttribute", 1) = 0 Then
                                objWorksheet.Cells(iRowNum, iCount + 1).Value = TableData(iCount).TagString
                            End If
                        End If
                    Next iCount
                    
                    iRowNum = iRowNum + 1
                    
                    For iCount = LBound(TableData) To UBound(TableData)
                        objWorksheet.Cells(iRowNum, iCount + 1).Value = TableData(iCount).TextString
                    Next iCount
                    
                    Header = True
                End If
            End If
        End With
    Next objEntity

    ' If we found attributes, then sort the column in Excel; otherwise,
    ' notify user that no attributes were found
    NumberOfAttributes = iRowNum - 1
    If NumberOfAttributes > 0 Then
        objWorksheet.Range("A1").Sort key1:=objWorksheet.Columns("A"), Header:=xlGuess
    Else
        MsgBox "No attributes found in the current drawing.", vbExclamation
    End If

ExitHere:
    Exit Function
    
HandleErr:
    MsgBox "ExportData error " & Err.Number & " (" & Err.Description & ") from " & _
            Err.Source, vbCritical, conDemoName
End Function

Public Sub ConnectExcel(X As Variant)
    ' X is only used to suppress this routine from the Run Macro dialog

    ' Determine the version of Excel available,
    ' and set the public variables accordingly
    
    On Error Resume Next
       
    ExcelVer = 0
    
    '---------------------------------
    ' Try to find a version of Excel 8
    '---------------------------------
    
    ' Attempt to activate an existing instance
    Err.Clear
    Set ExcelServer = GetObject(, "Excel.Application.8")
    If Err.Number = 0 Then
        ExcelVer = 8
        GoTo FINISH
    End If
    
    ' Create a new instance
    Err.Clear
    Set ExcelServer = CreateObject("Excel.Application.8")
    If Err.Number = 0 Then
        ExcelVer = 8
        GoTo FINISH
    End If
    
    '---------------------------------
    ' Try to find a version of Excel 7
    '---------------------------------
    
    ' Attempt to activate an existing instance
    Err.Clear
    Set ExcelServer = GetObject(, "Excel.Application.7")
    If Err.Number = 0 Then
        ExcelVer = 7
        GoTo FINISH
    End If
    
    ' Create a new instance
    Err.Clear
    Set ExcelServer = CreateObject("Excel.Application.7")
    If Err.Number = 0 Then
        ExcelVer = 7
        GoTo FINISH
    End If
    
FINISH:
    ' If we don't have Excel installed, do not run
    If (ExcelVer = 0) Then
        MsgBox "You must have Excel installed to run this sample", vbCritical, conDemoName
        Userform1.Hide
    End If

    ExcelServer.WindowState = -4140 ' xlMinimized
    ExcelServer.Visible = True  ' Make it visible
    
End Sub

Attribute VB_Name = "Userform1"
Attribute VB_Base = "0{EBF8B1B7-C099-4135-B443-D1BD41029366}{EE600979-4862-4C2C-BBA6-61506F27721D}"
Attribute VB_GlobalNameSpace = False
Attribute VB_Creatable = False
Attribute VB_PredeclaredId = True
Attribute VB_Exposed = False
Attribute VB_TemplateDerived = False
Attribute VB_Customizable = False
'      VBA Sample
'
'      Copyright (C) 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'
Option Explicit

Private Sub cmdGenerateReport_Click()
    ' Generate a report based on the current drawing
    
    On Error GoTo HandleErr
        
    ' Update status
    Userform1.lblStatus.Caption = "Exporting AutoCAD data to Excel..."
    
    ' If we found Excel, then continue
    If ExcelVer <> 0 Then GenerateDetailTable 1
        
    ' Update status
    Beep
    Userform1.lblStatus.Caption = "Finished exporting data to Excel..."
        
    Exit Sub
    
HandleErr:
    MsgBox "cmdGenerateReport_Click error " & Err.Number & " (" & Err.Description & ") from " & _
            Err.Source, vbCritical, conDemoName
End Sub

Private Sub cmdExit_Click()
    ' Ends the sample when the user clicks Exit
    Userform1.Hide
End Sub

Private Sub cmdImportBOM_Click()
    ' Update status
    Userform1.lblStatus.Caption = "Importing Excel data to AutoCAD..."
    
    ImportData 1
    
    ' Update status
    Beep
    Userform1.lblStatus.Caption = "Finished importing Excel data..."
End Sub

Private Sub UserForm_Initialize()
    ' This code is the first that gets run when the user launches
    ' the sample.
    
    On Error GoTo HandleErr
    
    ' Parts of this sample depend on Excel being present.
    ' Call a routine that sets public variables of
    ' this form to tell us whether its available.
    ConnectExcel 1
    
    Exit Sub
    
HandleErr:
    MsgBox "UserForm_Initialize error " & Err.Number & " (" & Err.Description & ") from " & _
            Err.Source, vbCritical, conDemoName
End Sub
