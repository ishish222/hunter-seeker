Attribute VB_Name = "Module1"
'      VBA Sample
'
'      Copyright (C) 1996, 1997, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.

Option Explicit

Global lineObject(0 To 11) As AcadLine
Global regionObject As Variant
Global solidObject As Acad3dSolid
Global beamWidth As Double
Global beamHeight As Double
Global beamWebThickness As Double
Global solidlength As Double
Global beamMI As Double
Global beamSectMod As Double
Global beamExists As Boolean
Public buffBlock As AcadBlock

Public Sub createIBeam(width As Double, height As Double, webThickness As Double, solidlength As Double)
    
    DefineBeam width, height, webThickness
    
    ' Build the 3dSolid (lines->region->extruded solid)
    regionObject = buffBlock.AddRegion(lineObject)
    Set solidObject = ThisDrawing.ModelSpace.AddExtrudedSolid(regionObject(0), solidlength, 0)
    
    beamExists = True
    
    ' Instantiate a view so we can interact with the model now
    Dim vportObj As Object
    Set vportObj = ThisDrawing.Viewports.Add("IBEAMVIEWPORT")
    ThisDrawing.ActiveViewport = vportObj
    ' Change the direction of the active viewport
    Dim newDirection(0 To 2) As Double
       newDirection(0) = 1#
       newDirection(1) = -1#
       newDirection(2) = 1#
    vportObj.Direction = newDirection
    ThisDrawing.ActiveViewport = vportObj
    ThisDrawing.Application.ZoomAll
    ' New direction takes effect

End Sub

Public Function checkRules(width As Double, height As Double, webThickness As Double) As Boolean
    Dim webHeight  As Double
    If (width > 0) And (height > 0) And (webThickness > 0) Then
        webHeight = height - 2 * webThickness
        If webHeight <= 0 Then
            Exit Function
        End If
        
        If (width > webThickness) And (height > webHeight) And (webThickness >= width / 6) _
            And (webHeight >= width / 4) Then
            checkRules = True
        End If
    End If
End Function

Sub IBeamVBA()
    UserForm1.Show
End Sub

Private Sub DefineBeam(width As Double, height As Double, webThickness As Double)
    Dim x(0 To 11) As Double
    Dim y(0 To 11) As Double
    Dim z As Double
    z = 0
    
    Dim halfFlange As Double
    halfFlange = (width - webThickness) / 2
    Dim halfHt As Double
    halfHt = height - 2 * webThickness
    
    x(0) = 0
    y(0) = 0
    
    x(1) = x(0) + width
    y(1) = y(0)
    x(2) = x(1)
    y(2) = y(1) + webThickness
    x(3) = x(2) - halfFlange
    y(3) = y(2)
    x(4) = x(3)
    y(4) = y(3) + halfHt
    x(5) = x(2)
    y(5) = y(4)
    x(6) = x(5)
    y(6) = y(5) + webThickness
    x(7) = x(0)
    y(7) = y(6)
    x(8) = x(0)
    y(8) = y(5)
    x(9) = x(8) + halfFlange
    y(9) = y(4)
    x(10) = x(9)
    y(10) = y(2)
    x(11) = x(0)
    y(11) = y(2)
    
    Dim insPt(0 To 2) As Double
    insPt(0) = 0:    insPt(1) = 0:    insPt(2) = 0
    
    Set buffBlock = ThisDrawing.Blocks.Add(insPt, "BUFFBLOCK")
    
    ' Build the lines for the region profile in the block
    Dim startPoint(0 To 2) As Double
    Dim endPoint(0 To 2) As Double
    Dim i As Integer
    Dim j As Integer
    For i = 0 To 11
        startPoint(0) = x(i)
        startPoint(1) = y(i)
        startPoint(2) = 0
        j = i + 1
        If i = 11 Then
            j = 0
        End If
        endPoint(0) = x(j)
        endPoint(1) = y(j)
        endPoint(2) = 0
        
        If beamExists Then
            lineObject(i).startPoint = startPoint
            lineObject(i).endPoint = endPoint
        Else
            Set lineObject(i) = buffBlock.AddLine(startPoint, endPoint)
        End If
    Next
End Sub

Public Sub UpdateBeam(width As Double, height As Double, webThickness As Double, solidlength As Double)
    DefineBeam width, height, webThickness
    
    ' Remove the old region before updating
    regionObject(0).Erase
    regionObject = buffBlock.AddRegion(lineObject)
    ' Remove the old solid before we update
    solidObject.Erase
    Set solidObject = ThisDrawing.ModelSpace.AddExtrudedSolid(regionObject(0), solidlength, 0)
    
    ThisDrawing.Application.ZoomExtents
    
    beamExists = True
End Sub

Public Function momentOfInteria(width As Double, height As Double, webThickness As Double) As Double
    Dim webHt As Double
    webHt = height - 2 * webThickness
    momentOfInteria = (width * height * height * height - webThickness * webHt * webHt * webHt) / 12
End Function

Public Function sectionModulus(width As Double, height As Double, webThickness As Double) As Double
    Dim mi As Double
    mi = momentOfInteria(width, height, webThickness)
    sectionModulus = (mi * 12) / (6 * height)
End Function

Attribute VB_Name = "UserForm1"
Attribute VB_Base = "0{EE7C0A2F-A63E-407E-A59B-72907A4AC868}{0310BFFF-E889-46E9-96E4-C5D6635707F4}"
Attribute VB_GlobalNameSpace = False
Attribute VB_Creatable = False
Attribute VB_PredeclaredId = True
Attribute VB_Exposed = False
Attribute VB_TemplateDerived = False
Attribute VB_Customizable = False
'      VBA Sample
'
'      Copyright (C) 1996, 1997, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.

Option Explicit

Private Sub ScrollBar1_Change()
    If beamExists Then
        If checkRules(scrlWidth.Value, beamHeight, beamWebThickness) Then
            beamWidth = scrlWidth.Value
            UpdateBeam beamWidth, beamHeight, beamWebThickness, solidlength
            UpdateMomentandSection beamWidth, beamHeight, beamWebThickness
        Else
            scrlWidth.Value = beamWidth
        End If
    End If
End Sub

Private Sub cmdCreateBeam_Click()
    ' Set global variables to reset the value in case checkRules fails
    beamWidth = scrlWidth.Value
    beamHeight = scrlHeight.Value
    beamWebThickness = scrlThickness.Value
    solidlength = scrlLength.Value

    ' If the parameters pass the rule, then create a beam
    If checkRules(beamWidth, beamHeight, beamWebThickness) Then
        createIBeam beamWidth, beamHeight, beamWebThickness, solidlength
        UpdateMomentandSection beamWidth, beamHeight, beamWebThickness
    Else
        MsgBox "Sorry, the beam cannot be created with your settings.", vbExclamation
        
        If Not (beamExists) Then
            MsgBox "Default settings restored.", vbInformation

            ' Set some initial values
            scrlWidth.Value = 650
            scrlHeight.Value = 650
            scrlThickness.Value = 125
            scrlLength.Value = 200
        End If
    End If
End Sub

Private Sub cmdQuit_Click()
' Unload the form (also calls Terminate event code)
    Unload Me
End Sub


Private Sub scrlHeight_Change()
    If beamExists = True Then
        If checkRules(beamWidth, scrlHeight.Value, beamWebThickness) Then
            beamHeight = scrlHeight.Value
            UpdateBeam beamWidth, beamHeight, beamWebThickness, solidlength
            UpdateMomentandSection beamWidth, beamHeight, beamWebThickness
        Else
            scrlHeight.Value = beamHeight
        End If
    End If
End Sub

Private Sub UpdateMomentandSection(beamWidth#, beamHeight#, beamWebThickness#)
    beamMI = momentOfInteria(beamWidth, beamHeight, beamWebThickness)
    beamSectMod = sectionModulus(beamWidth, beamHeight, beamWebThickness)
    Label8.Caption = Format(beamMI, "0.0000E+00")
    Label7.Caption = Format(beamSectMod, "0.0000E+00")
End Sub

Private Sub scrlLength_Change()
    If beamExists Then
          solidlength = scrlLength.Value
          UpdateBeam beamWidth, beamHeight, beamWebThickness, solidlength
          UpdateMomentandSection beamWidth, beamHeight, beamWebThickness
    End If
End Sub

Private Sub scrlThickness_Change()
    If beamExists Then
        If checkRules(beamWidth, beamHeight, scrlThickness.Value) Then
            beamWebThickness = scrlThickness.Value
            UpdateBeam beamWidth, beamHeight, beamWebThickness, solidlength
            UpdateMomentandSection beamWidth, beamHeight, beamWebThickness
        Else
            scrlThickness.Value = beamWebThickness
        End If
    End If
End Sub

Private Sub scrlWidth_Change()
    If beamExists Then
        If checkRules(scrlWidth.Value, beamHeight, beamWebThickness) Then
            beamWidth = scrlWidth.Value
            UpdateBeam beamWidth, beamHeight, beamWebThickness, solidlength
            UpdateMomentandSection beamWidth, beamHeight, beamWebThickness
        Else
            scrlWidth.Value = beamWidth
        End If
    End If
End Sub

Private Sub UserForm_Initialize()
' Set some initial values
    scrlWidth.Value = 650
    scrlHeight.Value = 650
    scrlThickness.Value = 125
    scrlLength.Value = 200
End Sub

Private Sub UserForm_Terminate()
' Cleanup
    Set solidObject = Nothing

' Delete our blockobject, if it exists
    Dim entry As Object
    For Each entry In ThisDrawing.Blocks
        If entry.Name = "BUFFBLOCK" Then
            buffBlock.Delete
        End If
    Next

' Reset the logic
    beamExists = False
End Sub
