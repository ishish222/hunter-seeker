Attribute VB_Name = "Form1"
Attribute VB_Base = "0{6996F312-9944-4860-9804-1ED38FA2069E}{CA6D9832-9F49-4E8A-8C1B-FEF906E0A053}"
Attribute VB_GlobalNameSpace = False
Attribute VB_Creatable = False
Attribute VB_PredeclaredId = True
Attribute VB_Exposed = False
Attribute VB_TemplateDerived = False
Attribute VB_Customizable = False
'      VBA Sample
'
'      Copyright (C) 1996, 1997, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.

Option Explicit

Private Sub cmdApply_Click()
    Dim elem As Object
    Dim Max, Min As Integer
    Dim i As Integer
    Dim NoOfIndices As Integer
    Dim Width, StartWidth, EndWidth As Double

    Width = CDbl(Text1.Text)
    If Width < 0# Then
        MsgBox "Please enter a positive value for the width"
    Else
        StartWidth = Width
        EndWidth = Width
        For Each elem In ThisDrawing.ModelSpace
            With elem
                If StrComp(.ObjectName, "AcDbPolyline", 1) = 0 Then
                    Max = UBound(.Coordinates)
                    Min = LBound(.Coordinates)
                    NoOfIndices = (Max - Min + 1) / 2
                    For i = 0 To NoOfIndices - 1
                        .SetWidth i, StartWidth, EndWidth
                    Next i
                    ' .Update  ' Uncomment to see each change
                End If
            End With
        Next elem
        ThisDrawing.Application.Update ' Do one Update
    End If
End Sub
Private Sub cmdCancel_Click()
    Unload Me
End Sub

Private Sub cmdHelp_Click()
    MsgBox "Changes the width of all polylines in ModelSpace." & Chr(13) & Chr(13) _
    & "You must first draw a polyline using the PLINE command."
End Sub

Private Sub SpinButton1_Change()
    Text1.Text = SpinButton1.Value / 10
End Sub

Private Sub UserForm_Click()

End Sub

Attribute VB_Name = "Module1"
'      VBA Sample
'
'      Copyright (C) 1996, 1997, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.


Option Explicit

Sub ChgPolyWidth()
    Form1.Show
End Sub
