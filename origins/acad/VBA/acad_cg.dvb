Attribute VB_Name = "Module1"
'      ActiveX Sample
'
'      Copyright (C) 1996, 1997, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.

Option Explicit

Public Sub ActiveXSample()
    UserForm1.Show
End Sub

Attribute VB_Name = "UserForm1"
Attribute VB_Base = "0{95874B64-1184-471E-83DC-31F3F8C646B2}{840B4C8F-640E-4090-9FE6-571EA8546A72}"
Attribute VB_GlobalNameSpace = False
Attribute VB_Creatable = False
Attribute VB_PredeclaredId = True
Attribute VB_Exposed = False
Attribute VB_TemplateDerived = False
Attribute VB_Customizable = False
'      VBA Sample
'
'      Copyright (C) 1996, 1997, 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.

Option Explicit

Public mospace As AcadModelSpace   'The model space object collection
Public paSpace As AcadPaperSpace   'The paper space object collection

Private Sub Check1_Click()
    ' The screen menu cannot update until the VBA dialog is dismissed
    ThisDrawing.Application.Preferences.Display.DisplayScreenMenu = Check1.Value
End Sub

Private Sub Check2_Click()
    ThisDrawing.Application.Preferences.Display.DisplayScrollBars = Check2.Value
End Sub

Private Sub CommandButton1_Click()
    'VBA is always linked to AutoCAD
    'Resize the AutoCAD window
    ThisDrawing.Application.WindowTop = 0
    ThisDrawing.Application.WindowLeft = 0
    ThisDrawing.Application.Width = 600
    ThisDrawing.Application.Height = 600
    MsgBox "The AutoCAD application has just been resized.", vbInformation
End Sub

Private Sub CommandButton10_Click()
    'Creating a modelspace viewport
    Dim vport As AcadViewport
    ThisDrawing.ActiveSpace = acModelSpace
    Set vport = ThisDrawing.Viewports.Add("NEW_VIEWPORT")
    vport.Split acViewport2Vertical
    ThisDrawing.ActiveViewport = vport
    
    'Creating a paperspace viewport
    Dim paSpace As AcadPaperSpace          'No need to declare paSpace here if
    Set paSpace = ThisDrawing.PaperSpace   'you declared it as a global
    Dim newVport As AcadPViewport          'Declare the viewport object variable
    Dim pt(0 To 2) As Double               'Declare the center point variable
    ThisDrawing.ActiveSpace = acPaperSpace 'Same as setting tilemode to 0
    pt(0) = 2.5                            'Set up center point for the new
    pt(1) = 7.5                            'viewport
    pt(2) = 0                              'Values other than 0 are ignored
                                           'Add the newVport viewport object
    Set newVport = paSpace.AddPViewport(pt, 6, 5)
    Dim viewDir(0 To 2) As Double          'Declare the view direction variable
    viewDir(0) = 1                         'Define the view direction vector
    viewDir(1) = 1
    viewDir(2) = 1
    newVport.Direction = viewDir           'Assign the direction to the viewport
    newVport.Display acOn                  'Enable the viewport
    ThisDrawing.MSpace = True              'Switch to model space (MSPACE command)
    ThisDrawing.ActivePViewport = newVport 'Set newVport current (not always
                                           'necessary but a good idea)
    ThisDrawing.Application.ZoomExtents    'ZOOM Extents in the new viewport
    ThisDrawing.MSpace = False             'Switch to paper space (PSPACE command)
    ThisDrawing.Application.ZoomAll        'ZOOM Extents in paper space
    
    ' Create several paperspace viewports
    Set paSpace = ThisDrawing.PaperSpace       'You declared it as a global
    Dim topVport, frontVport As AcadPViewport  'Define viewport object variables
    Dim rightVport, isoVport As AcadPViewport
    ThisDrawing.ActiveSpace = acPaperSpace
    
    'Create and set up topVport -------------------------------------------
    pt(0) = 2.5
    pt(1) = 7.5
    pt(2) = 0
    Set topVport = paSpace.AddPViewport(pt, 5, 5)
    
    'No need to set Direction for top view
    topVport.Display acOn
    ThisDrawing.MSpace = True
    ThisDrawing.ActivePViewport = topVport
    ThisDrawing.Application.ZoomExtents
    ThisDrawing.Application.ZoomScaled 0.5, acZoomScaledRelativePSpace
    
    'Create and set up frontVport -----------------------------------------
    pt(0) = 2.5
    pt(1) = 2.5
    pt(2) = 0
    Set frontVport = paSpace.AddPViewport(pt, 5, 5)
    viewDir(0) = 0
    viewDir(1) = 1
    viewDir(2) = 0
    frontVport.Direction = viewDir
    frontVport.Display acOn
    ThisDrawing.MSpace = True
    ThisDrawing.ActivePViewport = frontVport
    ThisDrawing.Application.ZoomExtents
    ThisDrawing.Application.ZoomScaled 0.5, acZoomScaledRelativePSpace
    
    'Create and set up rightVport -----------------------------------------
    pt(0) = 7.5
    pt(1) = 2.5
    pt(2) = 0
    Set rightVport = paSpace.AddPViewport(pt, 5, 5)
    viewDir(0) = 1
    viewDir(1) = 0
    viewDir(2) = 0
    rightVport.Direction = viewDir
    rightVport.Display acOn
    ThisDrawing.MSpace = True
    ThisDrawing.ActivePViewport = rightVport
    ThisDrawing.Application.ZoomExtents
    ThisDrawing.Application.ZoomScaled 0.5, acZoomScaledRelativePSpace
    
    'Create and set up isoVport -------------------------------------------
    pt(0) = 7.5
    pt(1) = 7.5
    pt(2) = 0
    Set isoVport = paSpace.AddPViewport(pt, 5, 5)
    viewDir(0) = 1
    viewDir(1) = 1
    viewDir(2) = 1
    isoVport.Direction = viewDir
    isoVport.Display acOn
    ThisDrawing.MSpace = True
    ThisDrawing.ActivePViewport = isoVport
    ThisDrawing.Application.ZoomExtents
    ThisDrawing.Application.ZoomScaled 0.5, acZoomScaledRelativePSpace
    
    'Finish up ------------------------------------------------------------
    ThisDrawing.MSpace = False
    ThisDrawing.Application.ZoomExtents
    ThisDrawing.Regen 1                        'Do a REGEN in all viewports
End Sub

Private Sub CommandButton11_Click()
    UserForm1.Hide
    
    Dim p1, p2 As Variant
    Dim NL As String
    NL = Chr(13) & Chr(10)                 'Define newline
    
    On Error Resume Next
    p1 = ThisDrawing.Utility.GetPoint(, NL & "First point: ")
    p2 = ThisDrawing.Utility.GetPoint(p1, NL & "Second point: ")
    
    If Err <> 0 Then
        MsgBox "Operation cancelled.", vbInformation
        Exit Sub
    End If
    
    'The following five lines of code calculate the distance between
    'points p1 and p2
    Dim x, y, z, dist As Double
    x = p1(0) - p2(0)
    y = p1(1) - p2(1)
    z = p1(2) - p2(2)
    dist = Sqr((Sqr((x ^ 2) + (y ^ 2)) ^ 2) + (z ^ 2))
    MsgBox Str(dist)                       'Display the resulting distance
    UserForm1.Show
    
End Sub

Private Sub CommandButton12_Click()
    UserForm1.Hide
    
    Dim sset As AcadSelectionSet     'Define sset as a SelectionSet object
 On Error Resume Next
 ' Delete the Selection Set if it Exists
 If Not IsNull(ThisDrawing.SelectionSets.Item("SS2")) Then
    Set sset = ThisDrawing.SelectionSets.Item("SS2")
    sset.Delete
 End If
    
    'Set sset to a new selection set named SS2 (the name doesn't matter here)
    Set sset = ThisDrawing.SelectionSets.Add("SS2")
    sset.SelectOnScreen                    'Prompt user to select objects
    
    'The following variable assignments define the xdata RegApp name and
    ' string values
    Dim appName, xdataStr As String
    appName = "MY_APP"
    xdataStr = "This is some xdata"
    
    'The following two variable definitions must be arrays of the same size.
    'The first variable holds integer values that define the types of the data
    'in the second variable. The first value (index 0) of one variable maps
    'to the same index of the other variable.
    Dim xdataType(0 To 1) As Integer       'Define xdataType for the data types
    Dim xdata(0 To 1) As Variant           'Define xdata for the data values
    
    'The following variable assignments define the values for each array.
    xdataType(0) = 1001                    '1001 indicates the RegApp name
    xdata(0) = appName                     'RegApp name string value
    xdataType(1) = 1000                    '1000 indicates a string value
    xdata(1) = xdataStr                    'Xdata string value
    
    'The following code loops through all entities in the selection set and
    'assigns the xdata to each entity.
    Dim ent As Object
    For Each ent In sset                  'For each entity in the selection set
       ent.SetXData xdataType, xdata      'assign the xdata
    Next ent
    
    'The following example displays the xdata attached with the previous example.
    ' If you attach xdata other than strings (type 1000), you will need to revise this code.
    Set sset = Nothing
    Set sset = ThisDrawing.SelectionSets.Add("SS3")
    sset.SelectOnScreen                     'Prompt user to select objects
    
    Dim xdataType1 As Variant               'Define xdataType to receive xdata types
    Dim xdata1 As Variant                   'Define xdata to receive xdata values
    Dim xd As Variant
    Dim xdi As Integer                      'Define integer variable index counter
    
    xdi = 0                                 'Set xdi to 0, tracks index of xdata
    Dim msgstr, NL As String                'Declare string variables for messages
    NL = Chr(13) & Chr(10)                  'Define newline
    appName = "MY_APP"                      'Define RegApp name to retrieve
    
    'Display message showing number of objects selected
    MsgBox Str(sset.Count) & " objects selected."
    For Each ent In sset                   'Loop for each entity in selection set
        msgstr = ""                        'Reset msgstr to a NULL string
        xdi = 0                            'Reset the index counter
    
        'Retrieve the appName xdata type and value for the entity
        ent.GetXData appName, xdataType1, xdata1
    
        'If the xdataType variable is not initialized, there was no appName xdata
        'to retrieve for that entity
        If VarType(xdataType1) <> vbEmpty Then
            For Each xd In xdata1          'Loop for each xdata value
                msgstr = msgstr & NL & Str(xdataType1(xdi)) & ": " & xd
                xdi = xdi + 1              'Increment the index counter
            Next xd                        'Next xdata value
        End If
    
        'If the msgstr variable is NULL, there was no xdata
        If msgstr = "" Then msgstr = NL & "NONE"
    
        'Display a message reporting the xdata for that entity
        MsgBox appName & " xdata on " & ent.EntityName & ":" & NL & msgstr
    Next ent                               'Next entity in selection set
    UserForm1.Show

End Sub

Private Sub CommandButton2_Click()
   Dim sysVarName As String
   Dim sysVarData As Variant
   Dim intSDI As Integer
   
    ' Check for MDI / SDI
   sysVarName = "SDI"
   sysVarData = ThisDrawing.GetVariable(sysVarName)
   intSDI = CInt(sysVarData)
   
    ' Opening a drawing file
    Dim dwgName As String
    dwgName = "c:\Campus.dwg"
    If Dir(dwgName) <> "" Then
       If intSDI = 0 Then
          ThisDrawing.Application.Documents.Open dwgName
       Else
          ThisDrawing.Open dwgName
       End If
    Else
        MsgBox "File " & dwgName & " does not exist.  A new file will be created."

    ' Starting a new drawing with the default template
    On Error Resume Next
    Dim templateFileName As String
    
    templateFileName = ThisDrawing.Application.Path & "\template\ansi-a.dwt"
       If intSDI = 0 Then
          ThisDrawing.Application.Documents.Add templateFileName
       Else
          ThisDrawing.New templateFileName
       End If
    If Err <> 0 Then
        MsgBox "The new file operation was cancelled.", vbInformation
    End If
    End If
    Set mospace = ThisDrawing.ModelSpace
    Set paSpace = ThisDrawing.PaperSpace

End Sub

Private Sub CommandButton3_Click()
    
    '------------------------------------------------------------------------
    ' Creating a Text Object that says "Hello World!" at 2,4,0 with height .5
    '------------------------------------------------------------------------
    Dim insPnt(0 To 2) As Double       'Declare insertion point variable
    Dim textHgt As Double              'Declare text height variable
    Dim textStr As String              'Declare text string variable
    Dim textObj As AcadText            'Declare text object variable
    insPnt(0) = 2                      'Assign X value to insertion point
    insPnt(1) = 1                      'Assign Y value to insertion point
    insPnt(2) = 0                      'Assign Z value to insertion point
    textHgt = 0.5                      'Set text height to .5
    textStr = "Hello World!"           'Set the text string
                                       'Create the text object
    Set textObj = mospace.AddText(textStr, insPnt, textHgt)
    textObj.Update
    
    '------------------------------------------------------------------------
    ' Creating a LightWeightPolyline Object
    '------------------------------------------------------------------------
    Dim lwpolyObj As AcadLWPolyline
    Dim ptArray(0 To 5) As Double
    ' Could use CreateTypedArray here
    ptArray(0) = 2                     'First coordinate (index 0 and 1)
    ptArray(1) = 4
    ptArray(2) = 3                     'Second coordinate (index 2 and 3)
    ptArray(3) = 2
    ptArray(4) = 4                     'Third coordinate (index 4 and 5)
    ptArray(5) = 4
    Set lwpolyObj = mospace.AddLightWeightPolyline(ptArray)
    lwpolyObj.Update
    '------------------------------------------------------------------------
    ' Creating a 3dSolid Box object
    '------------------------------------------------------------------------
    Dim boxObj As Acad3dSolid
    Dim boxOrigin(0 To 2) As Double
    Dim boxLength As Double
    Dim boxWidth As Double
    Dim boxHeight As Double
    boxOrigin(0) = 2
    boxOrigin(1) = 6
    boxOrigin(2) = 0
    boxLength = 1
    boxWidth = 2
    boxHeight = 1
    Set boxObj = mospace.AddBox(boxOrigin, boxLength, boxWidth, boxHeight)
    boxObj.Update
    ThisDrawing.Regen 1
End Sub

Private Sub CommandButton4_Click()
    Dim noMSObj As String
    Dim noPSObj As String
    Dim msgstr, NL As String             'Declare string variables
    NL = Chr(13) & Chr(10)               'Create a newline variable
    
    ' Get # of entities in ModelSpace and PaperSpace
    noMSObj = Str(mospace.Count)
    noPSObj = Str(paSpace.Count)
    If mospace.Count = 0 And paSpace.Count = 0 Then
        MsgBox "The current drawing is empty."
        Exit Sub
    End If
        
    MsgBox "The number of objects found is: " & NL & NL & "ModelSpace: " & noMSObj & NL & "PaperSpace: " & noPSObj
    
    ' Populate list box with list of entity names/types
    Dim ent As Object                    'Declare ent as an object
    List1.Clear                          'Clear the contents of the current list
    For Each ent In mospace              'Loop through the moSpace collection
        List1.AddItem ent.EntityName     'Add each entity name to the list box
    Next ent
    
    ' Display properties of the first Object in ModelSpace
    Set ent = mospace.Item(0)            'Set ent to the first object
    
    'Build the info string to display in the message box
    msgstr = "Information about the first model space entity." & NL & NL
    msgstr = msgstr & "Entity name: " & ent.EntityName & NL
    msgstr = msgstr & "Layer: " & ent.Layer & NL
    msgstr = msgstr & "Color: " & Str(ent.Color) & NL
    msgstr = msgstr & "Linetype: " & ent.Linetype & NL
    msgstr = msgstr & "Linetype scale: " & Str(ent.LinetypeScale) & NL
    msgstr = msgstr & "Handle: " & ent.Handle & NL
    msgstr = msgstr & "Visibility: " & ent.Visible
    MsgBox msgstr

    ' Modifying Entities in the database
    Set ent = mospace.Item(0)              'Set ent to the first object
    ent.Color = acRed                      'Change the Color property to red
    ent.Update                             'Update the entity on screen
    MsgBox "The color of the first object was set to red.", vbInformation
    
    ' Change the location of the first object (if it is a line)
    Set ent = mospace.Item(0)              'Set ent to the first object
    Dim p1(0 To 2) As Double               'Define p1 as an array of 3 doubles
    Dim p2(0 To 2) As Double               'Define p2 as an array of 3 doubles
    p1(0) = 1                              'Set the first (X) value of p1 to 12.0
    p1(1) = 1                              'Set the first (Y) value of p1 to 5.0
    p2(0) = 4                              'Set the first (X) value of p2 to 12.0
    p2(1) = 4                              'Set the first (Y) value of p2 to 7.0
    If ent.EntityName = "AcDbLine" Then    'If ent is a line, then
        ent.startPoint = p1                'Set the StartPoint property to p1
        ent.endPoint = p2                  'Set the EndPoint property to p2
        ent.Update                         'Update the entity on screen
        MsgBox "The first object was a line and its coordinates were changed to 1,1 - 4,4", vbInformation
    End If
    
    ' Force all circles to have a particular color and layer
    
    For Each ent In mospace                'Loop through the moSpace collection. If a circle then:
        If ent.EntityName = "AcDbCircle" Then
            ent.Color = acByLayer          'change the Color property to BYLAYER
            ent.Linetype = "BYLAYER"       'change the Linetype property to BYLAYER
            ent.Update                     'update the entity on screen
        End If
    Next ent
    MsgBox "The Color and LineType of all circles is now layer dependent.", vbInformation

    ' Retreiving the last entity in ModelSpace
    Set ent = mospace.Item(mospace.Count - 1)
    MsgBox "The last entity in the ModelSpace collection is: " & ent.EntityName

End Sub

Private Sub CommandButton5_Click()
    Dim NL As String
    
    UserForm1.Hide
    
    '--------------------------------------------------------------------
    'Get a String Input from the user.  User enters in the command line.
    '--------------------------------------------------------------------
    On Error Resume Next
    Dim retVal As String
    retVal = ThisDrawing.Utility.GetString(1, NL & "Enter your name: ")
    
    If Err <> 0 Then
        MsgBox "Operation cancelled.", vbInformation
    Else
        MsgBox "You Entered: " + retVal
    End If
    On Error GoTo 0
    
    '-------------------------------------------------------------------
    'Prompt for two points on the screen, then draw a line.
    '-------------------------------------------------------------------
    Dim stPnt, enPnt As Variant          'Define variables to receive return values
    Dim prompt1, prompt2 As String       'Define variables for prompt strings
    prompt1 = NL & "Start point: "
    prompt2 = NL & "End point: "
    
    '-------------------------------------------------------------------
    'Use GetPoint without the 'from point' to request a start point.
    '-------------------------------------------------------------------
    On Error Resume Next
    stPnt = ThisDrawing.Utility.GetPoint(, prompt1)
    
    If Err <> 0 Then
        MsgBox "Operation cancelled.", vbInformation
    Else
        'Use GetPoint using the start point as the 'from point' and request an end point
        enPnt = ThisDrawing.Utility.GetPoint(stPnt, prompt2)
        mospace.AddLine stPnt, enPnt 'Use AddLine to create a new line
    End If
    On Error GoTo 0
     
    '-------------------------------------------------------------------
    ' Get Keyword input from the user.
    '-------------------------------------------------------------------
    On Error Resume Next
    ThisDrawing.Utility.InitializeUserInput 0, "Line Circle Arc"
    retVal = ThisDrawing.Utility.GetKeyword(NL & "Enter an option (Line/Circle/<Arc>): ")
    
    If Err <> 0 Then
        MsgBox "Operation cancelled.", vbInformation
    Else
        If retVal = "" Then retVal = "Arc"      ' default if enter is pressed
        MsgBox "You Chose: " + retVal
    End If
    On Error GoTo 0
    
    
    'Controlling User Input
    Dim retInt As Integer                'Define integer variable
    Dim retStr, prmpt As String          'Define string variables
    
    'First parameter of InitializeUserInput (6) restricts input to positive
    'and non-negative values; second parameter is the list of valid keywords.
    ThisDrawing.Utility.InitializeUserInput 6, "Big Small Regular"
    
    'Set the prompt string variable
    prmpt = NL & "Enter size or (Big/Small/<Regular>): "
    
    'Entering a keyword at the GetInteger prompt causes an error; therefore to
    'allow your application to continue and check for the error description you
    'must set the error handler to resume on error.
    On Error Resume Next
    retInt = ThisDrawing.Utility.GetInteger(prmpt)
    
    'If the error description matches the one shown below, then use the value
    'of GetInput as the return value; otherwise, use the value of retInt.
    If Err.Description = "User input is a keyword" Then
        retStr = ThisDrawing.Utility.GetInput()
        MsgBox "Your input was an string/keyword: " & retStr 'Display the result
        Err.Clear
    Else
        If retInt = 0 Then               'If 0 the user must have pressed ENTER
            retStr = "Regular"           'Set retStr to "Regular"
            MsgBox "Your input was an keyword: " & retStr 'Display the result
        Else
            retStr = Str(retInt)         'Otherwise use the value of retInt
            MsgBox "Your input was an integer: " & Str(retInt) 'Display the result
        End If
    End If

    UserForm1.Show
    
End Sub

Private Sub CommandButton6_Click()
    UserForm1.Hide
    Dim sset As AcadSelectionSet         'Define sset as a SelectionSet object
    'Set sset to a new selection set named SS1 (the name doesn't matter here)
    Set sset = ThisDrawing.SelectionSets.Add("SS1")
    sset.SelectOnScreen                  'Prompt user to select objects
    Dim ent As Object                    'Define ent as an object
    For Each ent In sset                 'Loop through the SelectionSet collection
        ent.Color = acBlue               'Change the Color property to blue
        ent.Update                       'Update the entity on screen
    Next ent
    sset.Delete
    UserForm1.Show
End Sub

Private Sub CommandButton7_Click()
    Dim layerObj As Object
    Set layerObj = ThisDrawing.Layers.Add("LAYER1")
    layerObj.Color = acMagenta
    MsgBox "LAYER1 set to Magenta"
End Sub

Private Sub CommandButton9_Click()

    Dim plotObj As Object                  'Declare a plot object
    Dim plotConfigObj As Object            'Declare a plot configuration object
    Dim pt(0 To 2) As Double               'Declare a point variable
    Dim xy(0 To 1) As Double               'Declare a variable for scale and paper size
    Set plotObj = ThisDrawing.Plot         'Create the plot object
   
    On Error Resume Next                   'Enable error handling
    plotObj.PlotToFile "c:\temp\plot001"   'Plot to a file
    If Err Then                            'If the plot failed, return a message
        MsgBox "c:\temp\plot001 plot file already exists."
        Err.Clear
    End If

End Sub

Private Sub MultiPage1_Change()

End Sub

Private Sub SpinButton1_Change()
    Label1.Caption = "Cursor Size: " & SpinButton1.Value
    ThisDrawing.Application.Preferences.Display.CursorSize = SpinButton1.Value
End Sub

Private Sub UserForm_Initialize()
    '----------------------------------------------------------------------
    ' Initialize the ModelSpace and PaperSpace objects
    '----------------------------------------------------------------------
    Set mospace = ThisDrawing.ModelSpace
    Set paSpace = ThisDrawing.PaperSpace
    
    '----------------------------------------------------------------------
    ' Set value of preferences check boxes
    '----------------------------------------------------------------------
    Label1.Caption = "Cursor Size: " & ThisDrawing.Application.Preferences.Display.CursorSize
    SpinButton1.Value = ThisDrawing.Application.Preferences.Display.CursorSize
    
    Check1.Value = ThisDrawing.Application.Preferences.Display.DisplayScreenMenu
    Check2.Value = ThisDrawing.Application.Preferences.Display.DisplayScrollBars

End Sub
