Attribute VB_Name = "FrmCAOtest"
Attribute VB_Base = "0{C23A40E9-31E9-45C0-AC1E-463005290E20}{2743CC19-00D4-4462-A8CC-E55BA0332478}"
Attribute VB_GlobalNameSpace = False
Attribute VB_Creatable = False
Attribute VB_PredeclaredId = True
Attribute VB_Exposed = False
Attribute VB_TemplateDerived = False
Attribute VB_Customizable = False

' Global variables for dbConnect
Dim dbConnect As CAO.dbConnect
Dim linkTemplates As CAO.linkTemplates
Dim labelTemplates As CAO.labelTemplates
Dim linkSel As CAO.links

'Global variables for ADO
Dim ADOConnect As New ADODB.Connection
Dim rs As ADODB.Recordset
Dim currConnectionString As String

Private Sub cmdAttachedLabel_Click()
    Dim Doc As AcadDocument
    Set Doc = Documents.Item(listDrawings.List(listDrawings.ListIndex))
    If Doc Is Nothing Then Exit Sub
    
    ' Check if any row is selected and get the row if any row is selected
    If Me.listRows.SelectedItem Is Nothing Then
        MsgBox "Please select a row"
        Exit Sub
    ElseIf rs.CursorType = ADODB.adOpenForwardOnly Then
        MsgBox "The curorType is adOpenForwardOnly, I cannot support it now."
        Exit Sub
    End If
    rs.Move listRows.SelectedItem.index - 1, ADODB.adBookmarkFirst
    
    
    ' Get label template
    Dim labelTemplate As CAO.labelTemplate
    Set labelTemplate = dbConnect.GetLabelTemplates(Doc).Item(Me.ListView1.SelectedItem.Text)
    If labelTemplate Is Nothing Then
        MsgBox "Please select a label template"
        Exit Sub
    End If
    
    Dim linkTemplate As CAO.linkTemplate
    Dim blnFoundlinkTemplate As Boolean
    For Each linkTemplate In dbConnect.GetLinkTemplates(Doc)
        If linkTemplate.Table = labelTemplate.Table Then
            blnFoundlinkTemplate = True
            Exit For
        End If
    Next linkTemplate
    If blnFoundlinkTemplate <> True Then
        MsgBox "No link template found for Table " & labelTemplate.Table
        Exit Sub
    End If
    
    ' Set up KeyValues object
    Dim currKeyValues As CAO.KeyValues
    Set currKeyValues = GetInterfaceObject("CAO.KeyValues.16")
    ' Get each key description
    Dim OneKeyDesc As CAO.keyDescription
    Dim OneKeyValue As CAO.KeyValue
    Dim OneField As ADODB.Field
    For Each OneKeyDesc In linkTemplate.KeyDescriptions
        'Set OneKeyValue = AcadApplication.GetInterfaceObject("CAO.KeyValue")
        'OneKeyValue.FieldName = OneKeyDesc.FieldName
        For Each OneField In rs.Fields
            If StrComp(OneField.Name, OneKeyDesc.FieldName, 1) = 0 Then
                currKeyValues.Add OneKeyDesc.FieldName, OneField.Value
                Exit For
            End If
        Next OneField
        
    Next OneKeyDesc
    
    ' Select entities in AutoCAD
    Dim entitySet As IAcadSelectionSet

    FrmCAOtest.hide
    Set entitySet = Doc.ActiveSelectionSet
    entitySet.Clear
    entitySet.SelectOnScreen
    If entitySet.Count = 0 Then
        MsgBox "No entity is selected"
        FrmCAOtest.Show
        Exit Sub
    End If
    
    ' Create label
    Dim entityIndex As Integer
    Dim objectId As Long
    Dim newLabel As CAO.Label
    On Error Resume Next
    For entityIndex = 0 To entitySet.Count - 1
        objectId = entitySet.Item(entityIndex).objectId
        Set newLabel = linkTemplate.CreateLabel(objectId, currKeyValues, labelTemplate)
        If Err.Number <> 0 Then
            MsgBox "Unable to create attached label." + Err.Description
            Exit For
        End If
        newLabel.Reload
        newLabel.Refresh
    Next entityIndex

    FrmCAOtest.Show
End Sub

Private Sub cmdConnectDataSource_Click()
    Dim Doc As AcadDocument
    Set Doc = Documents.Item(listDrawings.List(listDrawings.ListIndex))
    If Doc Is Nothing Then Exit Sub
    
    Dim strDataSource As String
    Dim objQuery As CAO.Query
    Dim objLinkTemplate As CAO.linkTemplate
    Dim objLabelTemplate As CAO.labelTemplate
    If Me.ListView1.SelectedItem.SmallIcon = "link" Then
        Set objLinkTemplate = dbConnect.GetLinkTemplates(Doc).Item(Me.ListView1.SelectedItem.Text)
        If objLinkTemplate Is Nothing Then Exit Sub
        strDataSource = objLinkTemplate.DataSource
    ElseIf Me.ListView1.SelectedItem.SmallIcon = "label" Then
        Set objLabelTemplate = dbConnect.GetLabelTemplates(Doc).Item(Me.ListView1.SelectedItem.Text)
        If objLabelTemplate Is Nothing Then Exit Sub
        strDataSource = objLabelTemplate.DataSource
    ElseIf Me.ListView1.SelectedItem.SmallIcon = "query" Then
        Set objQuery = dbConnect.GetQueries(Doc).Item(Me.ListView1.SelectedItem.Text)
        If objQuery Is Nothing Then
            MsgBox "Error trying to retrieve Query object!"
            Exit Sub
        End If
        strDataSource = objQuery.DataSource
    End If
    If Not dbConnect.IsConnected(strDataSource) Then dbConnect.Connect strDataSource
    Dim strDataSourceLoc As String
    strDataSourceLoc = dbConnect.DataSourceLocation + "\"
    
    If ADOConnect.State = adStateOpen Then ADOConnect.Close
    Me.listRows.ListItems.Clear
    currConnectionString = "File Name=" + strDataSourceLoc + strDataSource + ".udl;User ID=;Password=;"
    ADOConnect.ConnectionString = currConnectionString
    ADOConnect.Open
    If ADOConnect.State = adStateOpen Then
        Dim msgStr As String
        msgStr = strDataSource + " is connected."
        msgStr = msgStr + vbCrLf + " Version = " + ADOConnect.Version
        msgStr = msgStr + " Provider = " + ADOConnect.Provider
        MsgBox msgStr
        LabelRowNum.Caption = "0 Rows"
        cmdShowTable.Enabled = True
        cmdShowLinkedRow.Enabled = True
'        cmdMakeLink.Enabled = True
'        cmdFSLabel.Enabled = True
'        cmdAttachedLabel.Enabled = True
    Else
        MsgBox "Unable to connect to " & strDataSource
    End If
End Sub

Private Sub cmdExit_Click()
    Unload Me
    End
End Sub

Private Sub cmdFSLabel_Click()
    Dim Doc As AcadDocument
    Set Doc = Documents.Item(listDrawings.List(listDrawings.ListIndex))
    If Doc Is Nothing Then Exit Sub
    
    ' Check if any row is selected and get the row if any row is selected
    If Me.listRows.SelectedItem Is Nothing Then
        MsgBox "Please select a row"
        Exit Sub
    ElseIf rs.CursorType = ADODB.adOpenForwardOnly Then
        MsgBox "The curorType is adOpenForwardOnly, I cannot support it now."
        Exit Sub
    End If
    rs.Move listRows.SelectedItem.index - 1, ADODB.adBookmarkFirst
    
    
    ' Get label template
    Dim labelTemplate As CAO.labelTemplate
    Set labelTemplate = dbConnect.GetLabelTemplates(Doc).Item(Me.ListView1.SelectedItem.Text)
    If labelTemplate Is Nothing Then
        MsgBox "Please select a label template"
        Exit Sub
    End If
    
    Dim linkTemplate As CAO.linkTemplate
    Dim blnFoundlinkTemplate As Boolean
    For Each linkTemplate In dbConnect.GetLinkTemplates(Doc)
        If linkTemplate.Table = labelTemplate.Table Then
            blnFoundlinkTemplate = True
            Exit For
        End If
    Next linkTemplate
    If blnFoundlinkTemplate <> True Then
        MsgBox "No link template found for Table " & labelTemplate.Table
        Exit Sub
    End If
    
    ' Set up KeyValues object
    Dim currKeyValues As CAO.KeyValues
    Set currKeyValues = GetInterfaceObject("CAO.KeyValues.16")
    ' Get each key description
    Dim OneKeyDesc As CAO.keyDescription
    Dim OneKeyValue As CAO.KeyValue
    Dim OneField As ADODB.Field
    For Each OneKeyDesc In linkTemplate.KeyDescriptions
        'Set OneKeyValue = AcadApplication.GetInterfaceObject("CAO.KeyValue")
        'OneKeyValue.FieldName = OneKeyDesc.FieldName
        For Each OneField In rs.Fields
            If StrComp(OneField.Name, OneKeyDesc.FieldName, 1) = 0 Then
                currKeyValues.Add OneKeyDesc.FieldName, OneField.Value
                Exit For
            End If
        Next OneField
        
    Next OneKeyDesc
    
    FrmCAOtest.hide
    Dim objUtility As AcadUtility
    Set objUtility = Doc.Utility
    Dim pt As Variant
    On Error Resume Next
    pt = objUtility.GetPoint(, "Specify point for label:")
    If Err Then Exit Sub
    On Error GoTo 0

    ' Create label
    Dim entityIndex As Integer
    Dim objectId As Long
    Dim newLabel As CAO.Label
    On Error Resume Next

    Set newLabel = linkTemplate.CreateLabel(pt, currKeyValues, labelTemplate)
    If Err.Number <> 0 Then
        MsgBox "Unable to create attached label." & vbCrLf & Err.Description, vbCritical
        Exit Sub
    End If
    newLabel.Reload
    
    FrmCAOtest.Show
End Sub

Private Sub cmdGetDrawings_Click()
    Dim Doc As AcadDocument
    listDrawings.Clear
    If Documents.Count > 0 Then
        For Each Doc In Documents
            listDrawings.AddItem Doc.Name
        Next Doc
        listDrawings.ListIndex = 0
    End If
End Sub

Private Sub cmdGetLabelTemplates_Click()
    Me.ListView1.ListItems.Clear
    Dim DocName As String
    DocName = listDrawings.List(listDrawings.ListIndex)
    If DocName = "" Then Exit Sub
    Dim Doc As AcadDocument
    Set Doc = AcadApplication.Documents.Item(DocName)
    If Doc Is Nothing Then Exit Sub
    Set labelTemplates = dbConnect.GetLabelTemplates(Doc)
    Dim objLabelTemplate As CAO.labelTemplate
    Dim objLinkTemplate As CAO.linkTemplate
    Dim itm As ListItem
    For Each objLabelTemplate In labelTemplates
        Set itm = Me.ListView1.ListItems.Add(, , objLabelTemplate.Name)
        itm.SmallIcon = Me.ImageList1.ListImages("label").Key
        Debug.Print itm.Text
        'listLabelTemplates.AddItem objLabelTemplate.Name
    Next objLabelTemplate
    Set linkTemplates = dbConnect.GetLinkTemplates(Doc)
    For Each objLinkTemplate In linkTemplates
        Set itm = Me.ListView1.ListItems.Add(, , objLinkTemplate.Name)
        itm.SmallIcon = Me.ImageList1.ListImages("link").Key
    Next objLinkTemplate
    Dim objQueries As CAO.Queries
    Dim objQuery As CAO.Query
    Set objQueries = dbConnect.GetQueries(Doc)
    For Each objQuery In objQueries
        Set itm = Me.ListView1.ListItems.Add(, , objQuery.Name)
        itm.SmallIcon = Me.ImageList1.ListImages("query").Key
    Next objQuery
End Sub

Private Sub cmdGetLinks_Click()
    Dim Doc As AutoCAD.AcadDocument
    Set Doc = Documents.Item(listDrawings.List(listDrawings.ListIndex))
    If Doc Is Nothing Then Exit Sub

    Dim objLinkTemplate As CAO.linkTemplate
    Dim objLabelTemplate As CAO.labelTemplate
    txtLinkData.Text = ""
    Debug.Print Me.ListView1.SelectedItem.index
    If Me.ListView1.SelectedItem.index = -1 Then Exit Sub
    If Me.ListView1.SelectedItem.SmallIcon = "link" Then
        Set objLinkTemplate = dbConnect.GetLinkTemplates(Doc).Item(Me.ListView1.SelectedItem.Text)
        If objLinkTemplate Is Nothing Then Exit Sub
    ElseIf Me.ListView1.SelectedItem.SmallIcon = "label" Then
        Set objLabelTemplate = dbConnect.GetLabelTemplates(Doc).Item(Me.ListView1.SelectedItem.Text)
        If objLabelTemplate Is Nothing Then Exit Sub
    End If
    
    ' Get links
    Dim linkTypes As Integer
    linkTypes = 0
    If CheckBoxEntityLink.Value = True Then linkTypes = linkTypes + CAO.kEntityLinkType
    If CheckBoxFSLabel.Value = True Then linkTypes = linkTypes + CAO.kFSLabelType
    If CheckBoxAttachedLabel.Value = True Then linkTypes = linkTypes + CAO.kAttachedLabelType
    If Me.ListView1.SelectedItem.SmallIcon = "link" Then
        ' Select entities which you query links on
        Dim entitySet As AcadSelectionSet
        FrmCAOtest.hide
        Set entitySet = Doc.ActiveSelectionSet
        entitySet.Clear
        entitySet.SelectOnScreen
        
        ' Add selected entity's objectId in an array
        If entitySet.Count = 0 Then
            MsgBox "No entity is selected"
            FrmCAOtest.Show
            Exit Sub
        End If
        Dim objIds() As Long
        ReDim objIds(0 To entitySet.Count - 1) As Long
        Dim index As Long
        For index = 0 To entitySet.Count - 1
            objIds(index) = entitySet.Item(index).objectId
        Next index
        Set linkSel = dbConnect.GetLinks(objLinkTemplate, objIds, linkTypes)
    ElseIf Me.ListView1.SelectedItem.SmallIcon = "label" Then
        Set linkSel = dbConnect.GetLinksByLabelTemplate(objLabelTemplate, linkTypes, Doc)
    End If
    
    If linkSel Is Nothing Then
        MsgBox "Unable to retrieve links, or no link in the selected entities."
        FrmCAOtest.Show
        Exit Sub
    ElseIf linkSel.Count = 0 Then
        MsgBox "No link in the selection set!"
        Set linkSel = Nothing
        On Error Resume Next
        FrmCAOtest.Show
        On Error GoTo 0
        Exit Sub
    End If
    Me.cmdShowLinkData.Enabled = True
    Me.cmdUpdateLink.Enabled = False
    Me.listRows.ListItems.Clear
    LabelTotalNumLinks.Caption = "1 of " + CStr(linkSel.Count)
    SpinButtonLinkIndex.Min = 1
    SpinButtonLinkIndex.Max = linkSel.Count
    SpinButtonLinkIndex.Value = 1
    If Me.ListView1.SelectedItem.SmallIcon = "link" Then
        entitySet.Clear
        Set entitySet = Nothing
    End If
    On Error Resume Next
    FrmCAOtest.Show
    On Error GoTo 0
End Sub

Private Sub cmdGetLinkTempData_Click()
    txtLinkTempData.Text = ""
    Dim Doc As AcadDocument
    Set Doc = Documents.Item(listDrawings.List(listDrawings.ListIndex))
    If Doc Is Nothing Then Exit Sub
    Dim obj As Object
    If Me.ListView1.SelectedItem.SmallIcon = "link" Then
        Set obj = dbConnect.GetLinkTemplates(Doc).Item(Me.ListView1.SelectedItem.Text)
        If obj Is Nothing Then Exit Sub
    ElseIf Me.ListView1.SelectedItem.SmallIcon = "label" Then
        Set obj = dbConnect.GetLabelTemplates(Doc).Item(Me.ListView1.SelectedItem.Text)
        If obj Is Nothing Then Exit Sub
    ElseIf Me.ListView1.SelectedItem.SmallIcon = "query" Then
        Set obj = dbConnect.GetQueries(Doc).Item(Me.ListView1.SelectedItem.Text)
        If obj Is Nothing Then
            MsgBox "Error trying to retrieve Query object!"
            Exit Sub
        End If
    Else
        Exit Sub
    End If
    If Not obj Is Nothing Then
        txtLinkTempData.Text = "Name:       " + obj.Name
        txtLinkTempData.Text = txtLinkTempData.Text + vbCrLf + "DataSource: " + obj.DataSource
        txtLinkTempData.Text = txtLinkTempData.Text + vbCrLf + "Catalog:    " + obj.Catalog
        txtLinkTempData.Text = txtLinkTempData.Text + vbCrLf + "Schema:     " + obj.Schema
        txtLinkTempData.Text = txtLinkTempData.Text + vbCrLf + "Table:      " + obj.Table
        
        ' Get each key description
        Dim OneKey As CAO.keyDescription
        Dim index As Integer
        Dim strOneKey As String
        index = 0
        If TypeName(obj) = "ILinkTemplate" Then
        For Each OneKey In obj.KeyDescriptions
            index = index + 1
            strOneKey = vbCrLf + "Key " + CStr(index) + ": "
            strOneKey = strOneKey + vbCrLf + "    " + "Name: " + OneKey.FieldName
            strOneKey = strOneKey + vbCrLf + "    " + "Type: " + CStr(OneKey.Type)
            strOneKey = strOneKey + vbCrLf + "    " + "DefinedSize: " + CStr(OneKey.DefinedSize)
            strOneKey = strOneKey + vbCrLf + "    " + "NumericScale: " + CStr(OneKey.NumericScale)
            strOneKey = strOneKey + vbCrLf + "    " + "Precision: " + CStr(OneKey.Precision)
            txtLinkTempData.Text = txtLinkTempData.Text + strOneKey
        Next OneKey
        ElseIf TypeName(obj) = "ILabelTemplate" Then
            txtLinkTempData.Text = txtLinkTempData.Text + vbCrLf + "Format:      " + obj.Format
        ElseIf TypeName(obj) = "IQuery" Then
            txtLinkTempData.Text = txtLinkTempData.Text + vbCrLf + "Text:      " + obj.Text
        End If
        txtLinkTempData.SetFocus
    End If
End Sub

Private Sub cmdInitDbConnect_Click()
    ThisDrawing.Activate
    ' Since CAO16.dll must be run inside AutoCAD process space,
    ' We MUST use AcadApplication.GetInterfaceObject(ProgID) to create any CAO objects.
    ' We cannot use normal CreateObject() or New to create any CAo objects
    Set dbConnect = GetInterfaceObject("CAO.DbConnect.16")
    If dbConnect Is Nothing Then
        MsgBox "Unable to create CAO.dbConnect Automation server."
        Exit Sub
    Else
        Dim msgStr As String
        msgStr = "CAO.dbConnect Automation server object is created!"
        msgStr = msgStr + vbCrLf + " Version = " + dbConnect.Version
        'MsgBox msgStr
        'cmdInitDbConnect.Enabled = False
        'cmdGetLinkTemps.Enabled = True
        cmdGetLabelTemplates.Enabled = True
        cmdReloadLabels.Enabled = True
        'cmdErrors.Enabled = True
    End If
End Sub

Private Sub cmdMakeLink_Click()
    Dim Doc As AcadDocument
    Set Doc = Documents.Item(listDrawings.List(listDrawings.ListIndex))
    If Doc Is Nothing Then Exit Sub
    
    ' Check if any row is selected and get the row if any row is selected
    If Me.listRows.SelectedItem Is Nothing Then
        MsgBox "Please select a row"
        Exit Sub
    ElseIf rs.CursorType = ADODB.adOpenForwardOnly Then
        MsgBox "The curorType is adOpenForwardOnly, I cannot support it now."
        Exit Sub
    End If
    rs.Move listRows.SelectedItem.index - 1, ADODB.adBookmarkFirst
'    rs.Move listRows.ListIndex - 1, ADODB.adBookmarkFirst
     'rs.Move listRows.ListIndex - 1, ADODB.adBookmarkFirst
    ' Get link template
    Dim linkTemplate As CAO.linkTemplate
    Set linkTemplate = dbConnect.GetLinkTemplates(Doc).Item(Me.ListView1.SelectedItem.Text)
    If linkTemplate Is Nothing Then
        MsgBox "Please select a link template"
        Exit Sub
    End If
    
    ' Set up KeyValues object
    Dim currKeyValues As CAO.KeyValues
    Set currKeyValues = GetInterfaceObject("CAO.KeyValues.16")
    ' Get each key description
    Dim OneKeyDesc As CAO.keyDescription
    Dim OneKeyValue As CAO.KeyValue
    Dim OneField As ADODB.Field
    For Each OneKeyDesc In linkTemplate.KeyDescriptions
        'Set OneKeyValue = AcadApplication.GetInterfaceObject("CAO.KeyValue")
        'OneKeyValue.FieldName = OneKeyDesc.FieldName
        For Each OneField In rs.Fields
            If StrComp(OneField.Name, OneKeyDesc.FieldName, 1) = 0 Then
                currKeyValues.Add OneKeyDesc.FieldName, OneField.Value
                Exit For
            End If
        Next OneField
        
    Next OneKeyDesc
    
    ' Select entities in AutoCAD
    Dim entitySet As IAcadSelectionSet

    FrmCAOtest.hide
    Set entitySet = Doc.ActiveSelectionSet
    entitySet.Clear
    entitySet.SelectOnScreen
    If entitySet.Count = 0 Then
        MsgBox "No entity is selected"
        FrmCAOtest.Show
        Exit Sub
    End If
    
    ' Create link
    Dim entityIndex As Integer
    Dim objectId As Long
    Dim newLink As CAO.link
    On Error Resume Next
    For entityIndex = 0 To entitySet.Count - 1
        objectId = entitySet.Item(entityIndex).objectId
        Set newLink = linkTemplate.CreateLink(objectId, currKeyValues)
        If Err.Number <> 0 Then
            MsgBox "Unable to create a link." + Err.Description
        End If
    Next entityIndex

    FrmCAOtest.Show
End Sub

Private Sub cmdReloadLabels_Click()
    Dim DocName As String
    DocName = listDrawings.List(listDrawings.ListIndex)
    If DocName = "" Then Exit Sub
    Dim Doc As IAcadDocument
    Set Doc = Documents.Item(DocName)
    If Doc Is Nothing Then Exit Sub
    
    ' Select entities which you query links on
    Dim entitySet As IAcadSelectionSet
    FrmCAOtest.hide
    Set entitySet = Doc.ActiveSelectionSet
    entitySet.Clear
    entitySet.SelectOnScreen
    
    ' Add selected entity's objectId in an array
    If entitySet.Count = 0 Then
        MsgBox "No entity is selected"
        FrmCAOtest.Show
        Exit Sub
    End If
    
    Dim objIds() As Long
    ReDim objIds(0 To entitySet.Count - 1) As Long
    Dim index As Long
    For index = 0 To entitySet.Count - 1
        objIds(index) = entitySet.Item(index).objectId
    Next index
   
    dbConnect.ReloadLabels (objIds)
    
    FrmCAOtest.Show
End Sub

Private Sub cmdShowLinkData_Click()
    If linkSel Is Nothing Then
        MsgBox "No link!"
        Exit Sub
    End If
    
    ' Get selected link
    Dim link As CAO.link
    Set link = linkSel.Item(SpinButtonLinkIndex.Value - 1)
    If link Is Nothing Then
        MsgBox "Unable to retrieve this link"
        Exit Sub
    End If
    
    'Clear controls
    ClearData
    
    txtLinkData.Text = "ObjectID: " + CStr(link.objectId)
    txtLinkData.Text = txtLinkData.Text + vbCrLf + "Link Template: " + link.linkTemplate.Name
    Select Case link.LinkType
    Case CAO.kEntityLinkType
        txtLinkData.Text = txtLinkData.Text + vbCrLf + "Link Type: Entity Link"
    Case CAO.kFSLabelType
        txtLinkData.Text = txtLinkData.Text + vbCrLf + "Link Type: Free Standing Label"
    Case CAO.kAttachedLabelType
        txtLinkData.Text = txtLinkData.Text + vbCrLf + "Link Type: Attached Label"
    Case Else
        txtLinkData.Text = txtLinkData.Text + vbCrLf + "Link Type: Unknown type"
    End Select
    txtLinkData.Text = txtLinkData.Text + vbCrLf + "KeyValues:"
    Dim OneKeyValue As CAO.KeyValue
    Dim strValue As String
    On Error Resume Next
    If link.KeyValues Is Nothing Then
        txtLinkData.Text = txtLinkData.Text + vbCrLf + "    " + "No key value is defined"
    Else
        ' Read key values
        Dim KeyIndex As Integer
        KeyIndex = 0
        For Each OneKeyValue In link.KeyValues
          Dim KeyType As Integer
          KeyType = VarType(OneKeyValue.Value)
          Select Case KeyType
          Case vbString
            strValue = OneKeyValue.Value
          Case vbInteger To vbDouble
            strValue = CStr(OneKeyValue.Value)
          Case vbBoolean
            If OneKeyValue.Value = True Then strValue = "True" Else strValue = "False"
          Case Else
            strValue = "Unknown type"
          End Select
          txtLinkData.Text = txtLinkData.Text + vbCrLf + "    " + OneKeyValue.FieldName + ": " + strValue
          
          ' Set KeyValue label and text for updating link
          If KeyIndex = 0 Then
            LabelKey1.Visible = True
            LabelKey1.Caption = OneKeyValue.FieldName
            txtKey1.Visible = True
            txtKey1.Text = strValue
          ElseIf KeyIndex = 1 Then
            LabelKey2.Visible = True
            LabelKey2.Caption = OneKeyValue.FieldName
            txtKey2.Visible = True
            txtKey2.Text = strValue
          ElseIf KeyIndex = 2 Then
            LabelKey3.Visible = True
            LabelKey3.Caption = OneKeyValue.FieldName
            txtKey3.Visible = True
            txtKey3.Text = strValue
          End If
          KeyIndex = KeyIndex + 1
        Next OneKeyValue
    End If
    Me.cmdUpdateLink.Enabled = True
    'txtLinkData.SetFocus
End Sub

Private Sub cmdShowLinkedRow_Click()
    If linkSel Is Nothing Then
        MsgBox "No link! Get links first."
        Exit Sub
    End If
    
    ' get link template
    Dim Doc As AutoCAD.AcadDocument
    Set Doc = Documents.Item(listDrawings.List(listDrawings.ListIndex))
    If Doc Is Nothing Then Exit Sub

    Dim objLinkTemplate As CAO.linkTemplate
    Dim objLabelTemplate As CAO.labelTemplate
'    txtLinkData.Text = ""
    Debug.Print Me.ListView1.SelectedItem.index
    If Me.ListView1.SelectedItem.index = -1 Then Exit Sub
    If Me.ListView1.SelectedItem.SmallIcon = "link" Then
        Set objLinkTemplate = dbConnect.GetLinkTemplates(Doc).Item(Me.ListView1.SelectedItem.Text)
        If objLinkTemplate Is Nothing Then Exit Sub
    ElseIf Me.ListView1.SelectedItem.SmallIcon = "label" Then
        Set objLabelTemplate = dbConnect.GetLabelTemplates(Doc).Item(Me.ListView1.SelectedItem.Text)
        If objLabelTemplate Is Nothing Then Exit Sub
    End If
    
    ' Show all linked rows based on LinkSel
    Dim Count, index, KeyIndex As Integer
    Dim rs As ADODB.Recordset
    Dim cmd As ADODB.Command
    Dim link As CAO.link
    Dim OneKeyValue As CAO.KeyValue
    Dim strWhere As String
    Dim strKeyValue As String
    Dim strKeyName As String
    
    ' Issue a query for each link
    listRows.ListItems.Clear
    Count = 0
    Set cmd = New ADODB.Command
    Set cmd.ActiveConnection = ADOConnect
    cmd.CommandTimeout = 30
    For index = 0 To linkSel.Count - 1
    'For Each link In linkSel
        Set link = linkSel.Item(index)
        If Me.ListView1.SelectedItem.SmallIcon = "link" Then
            If link.linkTemplate.Name <> objLinkTemplate.Name Then GoTo NextLink
        ElseIf Me.ListView1.SelectedItem.SmallIcon = "label" Then
            If link.Label.labelTemplate.Name <> objLabelTemplate.Name Then GoTo NextLink
        End If
        If link.KeyValues Is Nothing Then GoTo NextLink
        ' Read key values, build the where clause
        On Error Resume Next
        strWhere = ""
        KeyIndex = 0
        For Each OneKeyValue In link.KeyValues
            strKeyName = OneKeyValue.FieldName
            Select Case VarType(OneKeyValue.Value)
            Case vbString
                strKeyValue = "'" + OneKeyValue.Value + "'"
            Case vbInteger To vbDouble
                strKeyValue = CStr(OneKeyValue.Value)
            Case vbBoolean
                If OneKeyValue.Value = True Then strKeyValue = "True" Else strKeyValue = "False"
            Case Else
                strKeyValue = ""
            End Select
            If strKeyName <> "" And strKeyValue <> "" Then
                If strWhere = "" Then
                    strWhere = "Where " + strKeyName + " = " + strKeyValue
                Else
                    strWhere = strWhere + " and " + strKeyName + " = " + strKeyValue
                End If
            End If
            KeyIndex = KeyIndex + 1
        Next OneKeyValue
        If strWhere = "" Then GoTo NextLink
        
        ' Query database and get linked rows through ADO
        If Me.ListView1.SelectedItem.SmallIcon = "link" Then
            cmd.CommandText = "SELECT * from " + objLinkTemplate.Table + " " + strWhere
        ElseIf Me.ListView1.SelectedItem.SmallIcon = "label" Then
            cmd.CommandText = "SELECT * from " + objLabelTemplate.Table + " " + strWhere
        End If
        

        If Not rs Is Nothing Then Set rs = Nothing ' disconnect from last query
        Set rs = New ADODB.Recordset
        rs.Open cmd, , ADODB.adOpenDynamic, ADODB.adLockBatchOptimistic
        
        ' Show all fields
    Dim strColumnNames As String
    Dim Field As ADODB.Field
    Dim i As Long
    Dim lngCount As Long
    lngCount = Me.listRows.ColumnHeaders.Count
    For i = 1 To lngCount
        Call Me.listRows.ColumnHeaders.Remove(i)
    Next i

    Me.listRows.Enabled = True
    For Each Field In rs.Fields
        Call Me.listRows.ColumnHeaders.Add(, , Field.Name)
    Next Field
    
    'print field values for all records
    Count = 0
    Dim obj As Object
    Do While Not rs.EOF
        Count = Count + 1
        For i = 0 To rs.Fields.Count - 1
          Set Field = rs.Fields(i)
          Dim strValue As String
          Select Case VarType(Field.Value)
          Case vbString
            strValue = Field.Value
          Case vbInteger To vbDouble
            strValue = CStr(Field.Value)
          Case vbBoolean
            If Field.Value = True Then strValue = "True" Else strValue = "False"
          Case Else
            strValue = "<Unknown type>"
          End Select
          If i = 0 Then
            Set obj = Me.listRows.ListItems.Add(, , strValue)
          Else
            obj.SubItems(i) = strValue
          End If
        Next i
        rs.MoveNext
    Loop
        
NextLink:
    'Next link
    Next index
    
    LabelRowNum.Caption = CStr(Count) + " Rows"
End Sub

Private Sub cmdShowTable_Click()
    Me.listRows.ListItems.Clear
    Dim Doc As AcadDocument
    Set Doc = Documents.Item(listDrawings.List(listDrawings.ListIndex))
    If Doc Is Nothing Then Exit Sub
    Dim strTable As String
    Dim objQuery As CAO.Query
    Dim objLinkTemplate As CAO.linkTemplate
    Dim objLabelTemplate As CAO.labelTemplate
    If Me.ListView1.SelectedItem.SmallIcon = "link" Then
        Set objLinkTemplate = dbConnect.GetLinkTemplates(Doc).Item(Me.ListView1.SelectedItem.Text)
        If objLinkTemplate Is Nothing Then Exit Sub
        strTable = objLinkTemplate.Table
    ElseIf Me.ListView1.SelectedItem.SmallIcon = "label" Then
        Set objLabelTemplate = dbConnect.GetLabelTemplates(Doc).Item(Me.ListView1.SelectedItem.Text)
        If objLabelTemplate Is Nothing Then Exit Sub
        strTable = objLabelTemplate.Table
    ElseIf Me.ListView1.SelectedItem.SmallIcon = "query" Then
        Set objQuery = dbConnect.GetQueries(Doc).Item(Me.ListView1.SelectedItem.Text)
        If objQuery Is Nothing Then
            MsgBox "Error trying to retrieve Query object!"
            Exit Sub
        End If
        strTable = objQuery.Table
    End If
   
    ' Get recordset
    Dim cmd As ADODB.Command
    Set rs = Nothing
    Set rs = New ADODB.Recordset
    Set cmd = New ADODB.Command
    Set cmd.ActiveConnection = ADOConnect
    cmd.CommandText = "SELECT * from " + strTable
    'rs.Open cmd, , ADODB.adOpenDynamic, ADODB.adLockBatchOptimistic
    rs.Open cmd, , ADODB.adOpenKeyset, ADODB.adLockBatchOptimistic
    'LabelRowNum.Caption = CStr(rs.RecordCount) + " Rows"
    
    ' Show all fields
    'print field names
    Dim strColumnNames As String
    Dim Field As ADODB.Field
    Dim i As Long
    Dim lngCount As Long
    lngCount = Me.listRows.ColumnHeaders.Count
    For i = 1 To lngCount
        On Error Resume Next
        Call Me.listRows.ColumnHeaders.Remove(i)
        On Error GoTo 0
    Next i
    Me.listRows.Enabled = True
    For Each Field In rs.Fields
        Call Me.listRows.ColumnHeaders.Add(, , Field.Name)
    Next Field
    
    'print field values for all records
    Dim Count As Integer
    Count = 0
    Do While Not rs.EOF
        Count = Count + 1
        For i = 0 To rs.Fields.Count - 1
          Set Field = rs.Fields(i)
          Dim strValue As String
          Select Case VarType(Field.Value)
          Case vbString
            strValue = Field.Value
          Case vbInteger To vbDouble
            strValue = CStr(Field.Value)
          Case vbBoolean
            If Field.Value = True Then strValue = "True" Else strValue = "False"
          Case Else
            strValue = "<Unknown type>"
          End Select
          If i = 0 Then
            Set obj = Me.listRows.ListItems.Add(, , strValue)
          Else
            obj.SubItems(i) = strValue
          End If
        Next i
        rs.MoveNext
    Loop
    LabelRowNum.Caption = CStr(Count) + " Rows"
End Sub

Private Sub cmdUpdateLink_Click()
    If linkSel Is Nothing Then
        MsgBox "No link!"
        Exit Sub
    End If
    
    ' Get selected link
    Dim link As CAO.link
    Set link = linkSel.Item(SpinButtonLinkIndex.Value - 1)
    If link Is Nothing Then
        MsgBox "Unable to retrieve this link"
        Exit Sub
    End If
    
    ' Get link template and keydescriptions
    Dim linkTemplate As CAO.linkTemplate
    Set linkTemplate = link.linkTemplate
    'linkTemplates.Item(listLinkTemplates.ListIndex)
    'If linkTemplate Is Nothing Then
    '    MsgBox "Please select a link template"
    '    Exit Sub
    'End If
    Dim KeyDescs As CAO.KeyDescriptions
    Set KeyDescs = linkTemplate.KeyDescriptions
    
    ' Set new key values
    Dim KeyIndex As Integer
    Dim newKeyValues As CAO.KeyValues
    Set newKeyValues = AcadApplication.GetInterfaceObject("CAO.KeyValues.16")
    Dim OneKeyValue As CAO.KeyValue
    Dim OneKeyDesc As CAO.keyDescription
    Dim strKeyValue As String
    For KeyIndex = 0 To link.KeyValues.Count - 1
        Set OneKeyValue = link.KeyValues.Item(KeyIndex)
        strKeyValue = ""
        Select Case KeyIndex
        Case 0
            If OneKeyValue.FieldName = LabelKey1.Caption Then strKeyValue = txtKey1.Text
        Case 1
            If OneKeyValue.FieldName = LabelKey2.Caption Then strKeyValue = txtKey2.Text
        Case 2
            If OneKeyValue.FieldName = LabelKey3.Caption Then strKeyValue = txtKey3.Text
        End Select
        ' Convert to correct data type
        'Set OneKeyDesc = KeyDescs.Item(OneKeyValue.FieldName)
        Set OneKeyDesc = KeyDescs.Item(KeyIndex)
        Select Case OneKeyDesc.Type
        Case ADODB.adBoolean
            If strKeyValue = "True" Then
                OneKeyValue.Value = True
            ElseIf strKeyValue = "False" Then
                OneKeyValue.Value = False
            End If
        Case ADODB.adBSTR, ADODB.adChar
            OneKeyValue.Value = strKeyValue
        Case ADODB.adDouble
            OneKeyValue.Value = CDbl(strKeyValue)
        Case ADODB.adInteger
            OneKeyValue.Value = CInt(strKeyValue)
        End Select
        newKeyValues.Add OneKeyValue.FieldName, OneKeyValue.Value
    Next KeyIndex
    
    ' Update link
    link.KeyValues = newKeyValues
    If link.LinkType = kAttachedLabelType Or link.LinkType = kFSLabelType Then
        link.Label.Reload
        link.Label.Refresh
    End If
End Sub

Private Sub listLinkTemplates_Click()
    If ADOConnect.State = ADODB.adStateOpen Then
        Dim linkTemplate As CAO.linkTemplate
        Set linkTemplate = linkTemplates.Item(listLinkTemplates.ListIndex)
        If Not linkTemplate Is Nothing Then
            Dim strNewConnString As String
            Dim strDataSource As String
            Dim strDataSourceLoc As String
            strDataSourceLoc = dbConnect.DataSourceLocation + "\"
            strDataSource = linkTemplate.DataSource
            strNewConnString = "File Name=" + strDataSourceLoc + strDataSource + ".udl;User ID=;Password=;"
            If currConnectionString <> strNewConnString Then
                ADOConnect.Close
                cmdShowTable.Enabled = False
                cmdShowLinkedRow.Enabled = False
                cmdMakeLink.Enabled = False
            End If
        End If
    End If
End Sub



Private Sub ListView1_ItemClick(ByVal Item As MSComctlLib.ListItem)
    If Item.SmallIcon = "link" Then
        cmdGetLinkTempData.Enabled = True
        cmdGetLinks.Enabled = True
        cmdShowLinkData.Enabled = False
        cmdUpdateLink.Enabled = False
        cmdConnectDataSource.Enabled = True
        Me.cmdAttachedLabel.Enabled = False
        Me.cmdFSLabel.Enabled = False
        Set linkSel = Nothing
        Me.LabelTotalNumLinks.Caption = ""
        Me.cmdMakeLink.Enabled = True
        Me.cmdFSLabel.Enabled = False
        Me.cmdAttachedLabel.Enabled = False
    ElseIf Item.SmallIcon = "label" Then
        cmdGetLinkTempData.Enabled = True
        cmdGetLinks.Enabled = True
        cmdShowLinkData.Enabled = False
        cmdUpdateLink.Enabled = False
        cmdConnectDataSource.Enabled = True
        Me.cmdAttachedLabel.Enabled = True
        Me.cmdFSLabel.Enabled = True
        Set linkSel = Nothing
        Me.LabelTotalNumLinks.Caption = ""
        Me.cmdMakeLink.Enabled = False
        Me.cmdFSLabel.Enabled = True
        Me.cmdAttachedLabel.Enabled = True
    ElseIf Item.SmallIcon = "query" Then
        cmdGetLinkTempData.Enabled = True
        cmdGetLinks.Enabled = False
        cmdShowLinkData.Enabled = False
        cmdUpdateLink.Enabled = False
        cmdConnectDataSource.Enabled = True
        Me.cmdAttachedLabel.Enabled = False
        Me.cmdFSLabel.Enabled = False
        Set linkSel = Nothing
        Me.LabelTotalNumLinks.Caption = ""
        Me.cmdMakeLink.Enabled = False
        Me.cmdFSLabel.Enabled = False
        Me.cmdAttachedLabel.Enabled = False
    End If
    Dim obj As ListItem
    For Each obj In Me.ListView1.ListItems
        obj.Bold = False
    Next obj
    Item.Bold = True
    ClearData
End Sub

Private Sub SpinButtonLinkIndex_Change()
    If Not linkSel Is Nothing Then
        LabelTotalNumLinks.Caption = CStr(SpinButtonLinkIndex.Value) + " of " + CStr(linkSel.Count)
    End If
End Sub

Private Sub UserForm_Initialize()
    cmdInitDbConnect_Click
    cmdGetDrawings_Click
    Me.ImageList1.ImageWidth = 16
    Me.ImageList1.ImageHeight = 16
    With Me.ImageList1.ListImages
        Call .Add(, "link", LoadPicture(AcadApplication.Path & "\Sample\Database Connectivity\CAO\dbcm_link.bmp"))
        Call .Add(, "label", LoadPicture(AcadApplication.Path & "\Sample\Database Connectivity\CAO\dbcm_label.bmp"))
        Call .Add(, "query", LoadPicture(AcadApplication.Path & "\Sample\Database Connectivity\CAO\dbcm_query.bmp"))
    End With
    Dim obj As ColumnHeader
    With Me.ListView1
        .SortKey = 0
        .View = lvwReport
        .SmallIcons = Me.ImageList1
        .HideColumnHeaders = True
        Set obj = .ColumnHeaders.Add
        obj.Width = .Width - 5
        .FullRowSelect = True
        .LabelEdit = lvwManual
        .ListItems.Clear
        .HideSelection = False
    End With
    With Me.listRows
        .AllowColumnReorder = True
        '.Appearance = cc3D
        .SortKey = 0
        .View = lvwReport
        .HideColumnHeaders = False
        '.SmallIcons = Me.ImageList1
        Set obj = .ColumnHeaders.Add
        obj.Width = .Width - 5
        .FullRowSelect = True
        .LabelEdit = lvwManual
        .GridLines = True
        .ListItems.Clear
        .HideSelection = False
        '.Enabled = False
    End With
End Sub

Private Sub UserForm_Terminate()
    If Not linkSel Is Nothing Then Set linkSel = Nothing
    If Not linkTemplates Is Nothing Then Set linkTemplates = Nothing
    If Not dbConnect Is Nothing Then Set dbConnect = Nothing
    
    If Not rs Is Nothing Then Set rs = Nothing
    If ADOConnect.State = ADODB.adStateOpen Then ADOConnect.Close
End Sub

Private Sub ClearData()
    txtLinkData.Text = ""
    LabelKey1.Visible = False
    txtKey1.Visible = False
    LabelKey2.Visible = False
    txtKey2.Visible = False
    LabelKey3.Visible = False
    txtKey3.Visible = False
End Sub

Attribute VB_Name = "ThisDrawing"
Attribute VB_Base = "0{8E75D913-3D21-11D2-85C4-080009A0C626}"
Attribute VB_GlobalNameSpace = False
Attribute VB_Creatable = False
Attribute VB_PredeclaredId = True
Attribute VB_Exposed = True
Attribute VB_TemplateDerived = False
Attribute VB_Customizable = True
Public Sub main()
FrmCAOtest.Show 'vbModeless

End Sub
